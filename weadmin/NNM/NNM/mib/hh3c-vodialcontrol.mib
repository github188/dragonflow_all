-- ==========================================================================
-- Copyright (C) 2004 by H3C Technologies. All rights reserved.
--
-- Description: The purpose of this MIB file is to provide the definition of
--              voice dial control configuration.
-- Reference:
-- ==========================================================================
HH3C-VODIALCONTROL-MIB DEFINITIONS ::= BEGIN
    IMPORTS
        OBJECT-TYPE, MODULE-IDENTITY, IpAddress, Integer32
            FROM SNMPv2-SMI
        RowStatus
            FROM SNMPv2-TC
        CodecType
            FROM HH3C-VO-TYPE-MIB
        InetAddressType, InetAddress
            FROM INET-ADDRESS-MIB
        hh3cVoice
            FROM HH3C-OID-MIB;


        hh3cVoiceDialControl MODULE-IDENTITY
            LAST-UPDATED "200503150000Z"
            ORGANIZATION
                "Hangzhou H3C Tech. Co., Ltd."
            CONTACT-INFO
                "Platform Team Hangzhou H3C Tech. Co., Ltd.
                Hai-Dian District Beijing P.R. China
                http://www.h3c.com
                Zip:100085
                "
            DESCRIPTION
                "This MIB file is to provide the definition of
                 voice dial control configuration."
            REVISION "200503150000Z"
            DESCRIPTION
                "The initial version of this MIB file."
            ::= { hh3cVoice 5 }

--======================================
--          Type declaration
--======================================

        FaxProtocolType ::= INTEGER
            {
            nonstandardCompatible(1),
            t38(2),
            h323T38(3),
            sipT38(4),
            pcmG711alaw(5),
            pcmG711ulaw(6)
            }

        FaxBaudrateType ::= INTEGER
            {
            disable(1),
            voice(2),
            b2400(3),
            b4800(4),
            b9600(5),
            b14400(6)
            }

        FaxSupportModeType ::= INTEGER
            {
            rtp(1),
            vt(2),
            sip-udp(3)
            }

        FaxTrainMode ::= INTEGER
            {
            local(1),
            ppp(2)
            }

        PhoneNumberType ::= INTEGER
            {
                unknown(1),        -- The numbering type is unknown.
                abbreviated(2),    -- The numbering type is abbreviated.
                international(3),  -- The numbering type is international.
                national(4),       -- The numbering type is national.
                network(5),        -- The numbering type is network.
                reserved(6),       -- The numbering type is reserved.
                subscriber(7),     -- The numbering type is subscriber.
                initial(8)         -- The numbering type is initial.
            }

        PhoneNumberPlan ::= INTEGER
            {
                unknown(1),        -- The numbering plan is unknown.
                data(2),           -- Data numbering plan.
                isdn(3),           -- ISDN/telephone numbering plan.
                national(4),       -- National standard numbering plan.
                private(5),        -- Private numbering plan.
                reserved(6),       -- Reserved for extension.
                telex(7),          -- Telex numbering plan.
                initial(8)         -- Initial numbering plan.
            }


        hh3cVoPeerObjects OBJECT IDENTIFIER ::= { hh3cVoiceDialControl 1 }

--========================================================================
--                      hh3cVoPeerCommonConfigTable
--
--========================================================================
        hh3cVoPeerCommonConfigTable OBJECT-TYPE
            SYNTAX SEQUENCE OF HH3CVoPeerCommonConfigEntry
            MAX-ACCESS not-accessible
            STATUS current
            DESCRIPTION
                "This table contains the general voice peer information."
            ::= { hh3cVoPeerObjects 1 }


        hh3cVoPeerCommonConfigEntry OBJECT-TYPE
            SYNTAX HH3CVoPeerCommonConfigEntry
            MAX-ACCESS not-accessible
            STATUS current
            DESCRIPTION
                "The entry of hh3cVoPeerCommonConfigTable."
            INDEX { hh3cVoPeerCfgIndex }
            ::= { hh3cVoPeerCommonConfigTable 1 }


        HH3CVoPeerCommonConfigEntry ::=
            SEQUENCE {
                hh3cVoPeerCfgIndex
                    Integer32,
                hh3cVoPeerCfgRowStatus
                    RowStatus,
                hh3cVoPeerCfgType
                    INTEGER,
                hh3cVoPeerCfgDesPattern
                    OCTET STRING,
                hh3cVoPeerCfgCodec1st
                    CodecType,
                hh3cVoPeerCfgCodec2nd
                    CodecType,
                hh3cVoPeerCfgCodec3rd
                    CodecType,
                hh3cVoPeerCfgCodec4th
                    CodecType,
                hh3cVoPeerCfgDSCP
                    Integer32,
                hh3cVoPeerCfgShutDown
                    INTEGER,
                hh3cVoPeerCfgVADEnable
                    INTEGER,
                hh3cVoPeerCfgOutbandMode
                    INTEGER,
                hh3cVoPeerCfgFaxLevel
                    Integer32,
                hh3cVoPeerCfgFaxBaudrate
                    FaxBaudrateType,
                hh3cVoPeerCfgFaxLocalTrainPara
                    Integer32,
                hh3cVoPeerCfgFaxProtocol
                    FaxProtocolType,
                hh3cVoPeerCfgT38FaxHRPackNum
                    Integer32,
                hh3cVoPeerCfgT38FaxLRPackNum
                    Integer32,
                hh3cVoPeerCfgFaxSendNSFEnable
                    INTEGER,
                hh3cVoPeerCfgFaxSupportMode
                    FaxSupportModeType,
                hh3cVoPeerCfgFaxTrainMode
                    FaxTrainMode,
                hh3cVoPeerCfgFaxEcm
                    INTEGER,
                hh3cVoPeerCfgPriority
                    Integer32,
                hh3cVoPeerCfgDescription
                    OCTET STRING,
                hh3cVoPeerCfgCallingNumberType
                    PhoneNumberType,
                hh3cVoPeerCfgCalledNumberType
                    PhoneNumberType,
                hh3cVoPeerCfgCallingNumberPlan
                    PhoneNumberPlan,
                hh3cVoPeerCfgCalledNumberPlan
                    PhoneNumberPlan,
                hh3cVoPeerCfgSelectStop
                    INTEGER,
                hh3cVoPeerCfgCallingNumSubstRule
                    Integer32,
                hh3cVoPeerCfgCalledNumSubstRule
                    Integer32,
                hh3cVoPeerCfgMaxCall
                    Integer32
            }

        hh3cVoPeerCfgIndex OBJECT-TYPE
            SYNTAX Integer32 (1..2147483647)
            MAX-ACCESS not-accessible
            STATUS current
            DESCRIPTION
                "The index of a dial entity common table."
            ::= { hh3cVoPeerCommonConfigEntry 1 }


        hh3cVoPeerCfgRowStatus OBJECT-TYPE
            SYNTAX RowStatus
            MAX-ACCESS read-create
            STATUS current
            DESCRIPTION
                "This object is used to create, delete or modify a row in
                this table."
            ::= { hh3cVoPeerCommonConfigEntry 2 }


        hh3cVoPeerCfgType OBJECT-TYPE
            SYNTAX INTEGER
                {
                pots(1),
                voip(2),
                vofr(3)
                }
            MAX-ACCESS read-create
            STATUS current
            DESCRIPTION
                "The type of voice entity."
            ::= { hh3cVoPeerCommonConfigEntry 3 }


        hh3cVoPeerCfgDesPattern OBJECT-TYPE
            SYNTAX OCTET STRING
            MAX-ACCESS read-create
            STATUS current
            DESCRIPTION
                "This object indicates the caller number of this dial peer."
            ::= { hh3cVoPeerCommonConfigEntry 4 }


        hh3cVoPeerCfgCodec1st OBJECT-TYPE
            SYNTAX CodecType
            MAX-ACCESS read-create
            STATUS current
            DESCRIPTION
                "This object indicates the first desirable CODEC of speech
                of this dial peer."
            ::= { hh3cVoPeerCommonConfigEntry 5 }


        hh3cVoPeerCfgCodec2nd OBJECT-TYPE
            SYNTAX CodecType
            MAX-ACCESS read-create
            STATUS current
            DESCRIPTION
                "This object indicates the second desirable CODEC of speech
                of this dial peer."
            ::= { hh3cVoPeerCommonConfigEntry 6 }


        hh3cVoPeerCfgCodec3rd OBJECT-TYPE
            SYNTAX CodecType
            MAX-ACCESS read-create
            STATUS current
            DESCRIPTION
                "This object indicates the third desirable CODEC of speech
                of this dial peer."
            ::= { hh3cVoPeerCommonConfigEntry 7 }


        hh3cVoPeerCfgCodec4th OBJECT-TYPE
            SYNTAX CodecType
            MAX-ACCESS read-create
            STATUS current
            DESCRIPTION
                "This object indicates the forth desirable CODEC of speech
                of this dial peer."
            ::= { hh3cVoPeerCommonConfigEntry 8 }


        hh3cVoPeerCfgDSCP OBJECT-TYPE
            SYNTAX Integer32
            MAX-ACCESS read-create
            STATUS current
            DESCRIPTION
                "This object indicates the DSCP(Different Service Code Point)
                value of voice packets."
            ::= { hh3cVoPeerCommonConfigEntry 9 }


        hh3cVoPeerCfgShutDown OBJECT-TYPE
            SYNTAX INTEGER
                {
                enable(1),
                disable(2)
                }
            MAX-ACCESS read-create
            STATUS current
            DESCRIPTION
                "This object indicates the current status of this dial peer."
            ::= { hh3cVoPeerCommonConfigEntry 10 }


        hh3cVoPeerCfgVADEnable OBJECT-TYPE
            SYNTAX INTEGER
                {
                enable(1),
                disable(2)
                }
            MAX-ACCESS read-create
            STATUS current
            DESCRIPTION
                "This object indicates whether the VAD(Voice Activity Detection)
                is enabled."
            ::= { hh3cVoPeerCommonConfigEntry 11 }


        hh3cVoPeerCfgOutbandMode OBJECT-TYPE
            SYNTAX INTEGER
                {
                h245(1),
                voice(2),
                sip(3),
                h225(4)
                }
            MAX-ACCESS read-create
            STATUS current
            DESCRIPTION
                "This object indicates the DTMF(Dual Tone Multi-Frequency)
                outband type of this dial peer."
            ::= { hh3cVoPeerCommonConfigEntry 12 }


        hh3cVoPeerCfgFaxLevel OBJECT-TYPE
            SYNTAX Integer32
            MAX-ACCESS read-create
            STATUS current
            DESCRIPTION
                "This object indicates the fax level of this dial peer."
            ::= { hh3cVoPeerCommonConfigEntry 13 }


        hh3cVoPeerCfgFaxBaudrate OBJECT-TYPE
            SYNTAX FaxBaudrateType
            MAX-ACCESS read-create
            STATUS current
            DESCRIPTION
                "This object indicates the fax baudrate of this dial peer."
            ::= { hh3cVoPeerCommonConfigEntry 14 }


        hh3cVoPeerCfgFaxLocalTrainPara OBJECT-TYPE
            SYNTAX Integer32
            MAX-ACCESS read-create
            STATUS current
            DESCRIPTION
                "This object indicates the fax local train threshold of this
                dial peer."
            ::= { hh3cVoPeerCommonConfigEntry 15 }


        hh3cVoPeerCfgFaxProtocol OBJECT-TYPE
            SYNTAX FaxProtocolType
            MAX-ACCESS read-create
            STATUS current
            DESCRIPTION
                "This object indicates the fax protocol of this dial peer."
            ::= { hh3cVoPeerCommonConfigEntry 16 }


        hh3cVoPeerCfgT38FaxHRPackNum OBJECT-TYPE
            SYNTAX Integer32 (0..2)
            MAX-ACCESS read-create
            STATUS current
            DESCRIPTION
                "This object indicates the high speed redundancy packet
                numbers."
            ::= { hh3cVoPeerCommonConfigEntry 17 }


        hh3cVoPeerCfgT38FaxLRPackNum OBJECT-TYPE
            SYNTAX Integer32 (0..5)
            MAX-ACCESS read-create
            STATUS current
            DESCRIPTION
                "This object indicates the low speed redundancy packet
                numbers."
            ::= { hh3cVoPeerCommonConfigEntry 18 }


        hh3cVoPeerCfgFaxSendNSFEnable OBJECT-TYPE
            SYNTAX INTEGER
                {
                enable(1),
                disable(2)
                }
            MAX-ACCESS read-create
            STATUS current
            DESCRIPTION
                "This object indicates whether sends NSF(non-standard faculty)
                to fax of this dial peer."
            ::= { hh3cVoPeerCommonConfigEntry 19 }


        hh3cVoPeerCfgFaxSupportMode OBJECT-TYPE
            SYNTAX FaxSupportModeType
            MAX-ACCESS read-create
            STATUS current
            DESCRIPTION
                "This object indicates the fax support mode of this dial peer."
            ::= { hh3cVoPeerCommonConfigEntry 20 }


        hh3cVoPeerCfgFaxTrainMode OBJECT-TYPE
            SYNTAX FaxTrainMode
            MAX-ACCESS read-create
            STATUS current
            DESCRIPTION
                "This object indicates the fax train mode of this dial peer."
            ::= { hh3cVoPeerCommonConfigEntry 21 }


        hh3cVoPeerCfgFaxEcm OBJECT-TYPE
            SYNTAX INTEGER
                {
                enable(1),
                disalbe(2)
                }
            MAX-ACCESS read-create
            STATUS current
            DESCRIPTION
                "This object indicates whether the ECM(error correct mode)
                 is enabled."
            ::= { hh3cVoPeerCommonConfigEntry 22 }


        hh3cVoPeerCfgPriority OBJECT-TYPE
            SYNTAX Integer32
            MAX-ACCESS read-create
            STATUS current
            DESCRIPTION
                "This object indicates the priority of this dial peer."
            ::= { hh3cVoPeerCommonConfigEntry 23 }


        hh3cVoPeerCfgDescription   OBJECT-TYPE
            SYNTAX OCTET STRING
            MAX-ACCESS read-create
            STATUS current
            DESCRIPTION
                "This object indicates the textual description of this
                dial peer."
            ::= { hh3cVoPeerCommonConfigEntry 24 }


        hh3cVoPeerCfgCallingNumberType   OBJECT-TYPE
            SYNTAX PhoneNumberType
            MAX-ACCESS read-create
            STATUS current
            DESCRIPTION
                "This object indicates the type of calling number
                of this dial peer."
            ::= { hh3cVoPeerCommonConfigEntry 25 }


        hh3cVoPeerCfgCalledNumberType   OBJECT-TYPE
            SYNTAX PhoneNumberType
            MAX-ACCESS read-create
            STATUS current
            DESCRIPTION
                "This object indicates the type of called number
                of this dial peer."
            ::= { hh3cVoPeerCommonConfigEntry 26 }


        hh3cVoPeerCfgCallingNumberPlan   OBJECT-TYPE
            SYNTAX PhoneNumberPlan
            MAX-ACCESS read-create
            STATUS current
            DESCRIPTION
                "This object indicates the numbering plan of calling
                number of this dial peer."
            ::= { hh3cVoPeerCommonConfigEntry 27 }


        hh3cVoPeerCfgCalledNumberPlan   OBJECT-TYPE
            SYNTAX PhoneNumberPlan
            MAX-ACCESS read-create
            STATUS    current
            DESCRIPTION
                "This object indicates the numbering plan of called
                number of this dial peer."
        ::= { hh3cVoPeerCommonConfigEntry 28 }


        hh3cVoPeerCfgSelectStop   OBJECT-TYPE
            SYNTAX INTEGER
                {
                enable(1),
                disable(2)
                }
            MAX-ACCESS read-create
            STATUS current
            DESCRIPTION
                "This object indicates whether permitting the system
                to allocate alternative entities to establish a phone
                call."
            ::= { hh3cVoPeerCommonConfigEntry 29 }


        hh3cVoPeerCfgCallingNumSubstRule   OBJECT-TYPE
            SYNTAX Integer32(0..2147483647)
            MAX-ACCESS read-create
            STATUS current
            DESCRIPTION
                "This object indicates number-substitute rule of calling
                number."
            ::= { hh3cVoPeerCommonConfigEntry 30 }


        hh3cVoPeerCfgCalledNumSubstRule   OBJECT-TYPE
            SYNTAX Integer32(0..2147483647)
            MAX-ACCESS read-create
            STATUS current
            DESCRIPTION
                "This object indicates number-substitute rule of called
                number."
            ::= { hh3cVoPeerCommonConfigEntry 31 }


        hh3cVoPeerCfgMaxCall   OBJECT-TYPE
            SYNTAX Integer32(0..2147483647)
            MAX-ACCESS read-create
            STATUS current
            DESCRIPTION
                "The object indicates that this dial peer is bound with a tag that
                indicates a maximum call value."
            ::= {  hh3cVoPeerCommonConfigEntry 32 }



--========================================================================
--                      hh3cVoPOTSPeerConfigTable
--
--========================================================================
        hh3cVoPOTSPeerConfigTable OBJECT-TYPE
            SYNTAX SEQUENCE OF HH3CVoPOTSPeerConfigEntry
            MAX-ACCESS not-accessible
            STATUS current
            DESCRIPTION
                "This table contains the POTS(Public Switched Telephone Network)
                peer information."
            ::= { hh3cVoPeerObjects 2 }


        hh3cVoPOTSPeerConfigEntry OBJECT-TYPE
            SYNTAX HH3CVoPOTSPeerConfigEntry
            MAX-ACCESS not-accessible
            STATUS current
            DESCRIPTION
                "The entry of hh3cVoPOTSPeerConfigTable."
            INDEX { hh3cVoPOTSPeerConfigIndex }
            ::= { hh3cVoPOTSPeerConfigTable 1 }


        HH3CVoPOTSPeerConfigEntry ::=
            SEQUENCE {
                hh3cVoPOTSPeerConfigIndex
                    Integer32,
                hh3cVoPOTSPeerConfigPrefix
                    OCTET STRING,
                hh3cVoPOTSPeerConfigSubLine
                    OCTET STRING,
                hh3cVoPOTSPeerConfigSendNum
                    Integer32
             }

        hh3cVoPOTSPeerConfigIndex OBJECT-TYPE
            SYNTAX Integer32 (1..2147483647)
            MAX-ACCESS not-accessible
            STATUS current
            DESCRIPTION
                "The index of voice pots peer table."
            ::= { hh3cVoPOTSPeerConfigEntry 1 }


        hh3cVoPOTSPeerConfigPrefix OBJECT-TYPE
            SYNTAX OCTET STRING
            MAX-ACCESS read-write
            STATUS current
            DESCRIPTION
                "This object indicates the prefix which is added to the
                called number."
            ::= { hh3cVoPOTSPeerConfigEntry 2 }


        hh3cVoPOTSPeerConfigSubLine OBJECT-TYPE
            SYNTAX OCTET STRING
            MAX-ACCESS read-write
            STATUS current
            DESCRIPTION
                "This object indicates the voice subscriber line of
                this dial peer."
            ::= { hh3cVoPOTSPeerConfigEntry 3 }


        hh3cVoPOTSPeerConfigSendNum OBJECT-TYPE
            SYNTAX Integer32
            MAX-ACCESS read-write
            STATUS current
            DESCRIPTION
                "This object indicates the digit of phone number to be
                sent to the destination."
            ::= { hh3cVoPOTSPeerConfigEntry 4 }



--========================================================================
--                      hh3cVoVoIPPeerConfigTable
--
--========================================================================
        hh3cVoVoIPPeerConfigTable OBJECT-TYPE
            SYNTAX SEQUENCE OF HH3CVoVoIPPeerConfigEntry
            MAX-ACCESS not-accessible
            STATUS current
            DESCRIPTION
                "This table contains the voip peer information."
            ::= { hh3cVoPeerObjects 3 }


        hh3cVoVoIPPeerConfigEntry OBJECT-TYPE
            SYNTAX HH3CVoVoIPPeerConfigEntry
            MAX-ACCESS not-accessible
            STATUS current
            DESCRIPTION
                "The entry of hh3cVoVoIPPeerConfigTable."
            INDEX { hh3cVoVoIPPeerCfgIndex }
            ::= { hh3cVoVoIPPeerConfigTable 1 }


        HH3CVoVoIPPeerConfigEntry ::=
            SEQUENCE {
                hh3cVoVoIPPeerCfgIndex
                    Integer32,
                hh3cVoVoIPPeerCfgTargetType
                    INTEGER,
                hh3cVoVoIPPeerCfgTargetAddrType
                    InetAddressType,
                hh3cVoVoIPPeerCfgTargetAddr
                    InetAddress,
                hh3cVoVoIPPeerCfgFastStart
                    INTEGER,
                hh3cVoVoIPPeerCfgTunnel
                    INTEGER,
                hh3cVoVoIPPeerCfgAreaID
                    OCTET STRING,
                hh3cVoVoIPPeerCfgSendRing
                    INTEGER
             }

        hh3cVoVoIPPeerCfgIndex OBJECT-TYPE
            SYNTAX Integer32 (1..2147483647)
            MAX-ACCESS not-accessible
            STATUS current
            DESCRIPTION
                "The index of voice voip peer table."
            ::= { hh3cVoVoIPPeerConfigEntry 1 }


        hh3cVoVoIPPeerCfgTargetType OBJECT-TYPE
            SYNTAX INTEGER
                {
                unknown(1),
                ras(2),
                h323IpAddress(3),
                sipIpAddress(4),
                sipProxy(5)
                }
            MAX-ACCESS read-write
            STATUS current
            DESCRIPTION
                "This object indicates the type of the session target of this peer."
            ::= { hh3cVoVoIPPeerConfigEntry 2 }


        hh3cVoVoIPPeerCfgTargetAddrType OBJECT-TYPE
            SYNTAX  InetAddressType
            MAX-ACCESS read-write
            STATUS current
            DESCRIPTION
                "The IP address type of object hh3cVoVoIPPeerCfgTargetAddr."
            ::= { hh3cVoVoIPPeerConfigEntry 3 }


        hh3cVoVoIPPeerCfgTargetAddr OBJECT-TYPE
            SYNTAX InetAddress
            MAX-ACCESS read-write
            STATUS current
            DESCRIPTION
                "This object indicates the target ip address. This object is
                valid when hh3cVoVoIPPeerCfgTargetType is h323Ipv4 or sipIpv4."
            ::= { hh3cVoVoIPPeerConfigEntry 4 }


        hh3cVoVoIPPeerCfgFastStart OBJECT-TYPE
            SYNTAX INTEGER
                {
                enable(1),
                disable(2)
                }
            MAX-ACCESS read-write
            STATUS current
            DESCRIPTION
                "This object indicates whether the fast connection function
                is enabled."
           ::= { hh3cVoVoIPPeerConfigEntry 5 }


        hh3cVoVoIPPeerCfgTunnel OBJECT-TYPE
            SYNTAX INTEGER
                {
                enable(1),
                disable(2)
                }
            MAX-ACCESS read-write
            STATUS current
            DESCRIPTION
                "This object indicates whether the tunnel function
                is enabled."
            ::= { hh3cVoVoIPPeerConfigEntry 6 }


        hh3cVoVoIPPeerCfgAreaID OBJECT-TYPE
            SYNTAX OCTET STRING
            MAX-ACCESS read-write
            STATUS current
            DESCRIPTION
                "This object specifies service area-id."
            ::= { hh3cVoVoIPPeerConfigEntry 7 }


        hh3cVoVoIPPeerCfgSendRing OBJECT-TYPE
            SYNTAX INTEGER
                {
                enable(1),
                disable(2)
                }
            MAX-ACCESS read-write
            STATUS current
            DESCRIPTION
                "This object indicates whether sending ring is enabled."
            ::= { hh3cVoVoIPPeerConfigEntry 8 }


--========================================================================
--                      hh3cVoPeerDefaultConfigObjects
--
--========================================================================
        hh3cVoPeerDefaultConfigObjects OBJECT IDENTIFIER ::= { hh3cVoPeerObjects 4 }

        hh3cVoPeerDefault1stCodecLevel OBJECT-TYPE
            SYNTAX CodecType
            MAX-ACCESS read-write
            STATUS current
            DESCRIPTION
                "The default priority of the first level CODEC(coding and
                decoding)."
            ::= { hh3cVoPeerDefaultConfigObjects 2 }


        hh3cVoPeerDefault2ndCodecLevel OBJECT-TYPE
            SYNTAX CodecType
            MAX-ACCESS read-write
            STATUS current
            DESCRIPTION
                "The default priority of the second level CODEC(coding and
                decoding)."
            ::= { hh3cVoPeerDefaultConfigObjects 3 }


        hh3cVoPeerDefault3rdCodecLevel OBJECT-TYPE
            SYNTAX CodecType
            MAX-ACCESS read-write
            STATUS current
            DESCRIPTION
                "The default priority of the third level CODEC(coding and
                decoding)."
            ::= { hh3cVoPeerDefaultConfigObjects 4 }


        hh3cVoPeerDefault4thCodecLevel OBJECT-TYPE
            SYNTAX CodecType
            MAX-ACCESS read-write
            STATUS current
            DESCRIPTION
                "The default priority of the fourth level CODEC(coding and
                decoding)."
            ::= { hh3cVoPeerDefaultConfigObjects 5 }


        hh3cVoPeerDefaultVADOn OBJECT-TYPE
            SYNTAX INTEGER
                {
                enable(1),
                disable(2)
                }
            MAX-ACCESS read-write
            STATUS current
            DESCRIPTION
                "The default value of dial peer's VAD(Voice Activity Detection)."
            ::= { hh3cVoPeerDefaultConfigObjects 6 }


        hh3cVoPeerDefaultFaxTransLevel OBJECT-TYPE
            SYNTAX Integer32
            MAX-ACCESS read-write
            STATUS current
            DESCRIPTION
                "The default value of dial peer's fax transmit level.
                The unit is db."
            ::= { hh3cVoPeerDefaultConfigObjects 7 }


        hh3cVoPeerDefaultFaxLocalTrain OBJECT-TYPE
            SYNTAX Integer32
            MAX-ACCESS read-write
            STATUS current
            DESCRIPTION
                "The default value of dial peer's fax local train threshold."
            ::= { hh3cVoPeerDefaultConfigObjects 8 }


        hh3cVoPeerDefaultFaxProtocol OBJECT-TYPE
            SYNTAX FaxProtocolType
            MAX-ACCESS read-write
            STATUS current
            DESCRIPTION
                "The default value of dial peer's fax protocol."
            ::= { hh3cVoPeerDefaultConfigObjects 9 }


        hh3cVoPeerDefaultFaxHSRedunNum OBJECT-TYPE
            SYNTAX Integer32 (0..2)
            MAX-ACCESS read-write
            STATUS current
            DESCRIPTION
                "The default value of dial peer's T38 fax protocol high
                redundancy packet number."
            ::= { hh3cVoPeerDefaultConfigObjects 10 }


        hh3cVoPeerDefaultFaxLSRedunNum OBJECT-TYPE
            SYNTAX Integer32 (0..5)
            MAX-ACCESS read-write
            STATUS current
            DESCRIPTION
                "The default value of dial peer's T38 fax protocol low
                redundancy packet number."
            ::= { hh3cVoPeerDefaultConfigObjects 11 }


        hh3cVoPeerDefaultFaxBaudrate OBJECT-TYPE
            SYNTAX FaxBaudrateType
            MAX-ACCESS read-write
            STATUS current
            DESCRIPTION
                "The default value of dial peer's fax baudrate."
            ::= { hh3cVoPeerDefaultConfigObjects 12 }


        hh3cVoPeerDefaultFaxNSF OBJECT-TYPE
            SYNTAX INTEGER
                {
                enable(1),
                disable(2)
                }
            MAX-ACCESS read-write
            STATUS current
            DESCRIPTION
                "The default value of fax NSF(non-standard faculty)."
            ::= { hh3cVoPeerDefaultConfigObjects 13 }


        hh3cVoPeerDefaultFaxSupportMode OBJECT-TYPE
            SYNTAX FaxSupportModeType
            MAX-ACCESS read-write
            STATUS current
            DESCRIPTION
                "The default mode of fax supported."
            ::= { hh3cVoPeerDefaultConfigObjects 14 }


        hh3cVoPeerDefaultFaxTrainMode OBJECT-TYPE
            SYNTAX FaxTrainMode
            MAX-ACCESS read-write
            STATUS current
            DESCRIPTION
                "The default value of fax training mode."
            ::= { hh3cVoPeerDefaultConfigObjects 15 }


        hh3cVoPeerDefaultFaxECM OBJECT-TYPE
            SYNTAX INTEGER
                {
                enable(1),
                disable(2)
                }
            MAX-ACCESS read-write
            STATUS current
            DESCRIPTION
                "The default value of fax ECM(Error Correct Mode) Mode."
            ::= { hh3cVoPeerDefaultConfigObjects 16 }


--========================================================================
--                      hh3cVoPeerCfgCallerPermitTable
--
--========================================================================
        hh3cVoPeerCfgCallerPermitTable OBJECT-TYPE
            SYNTAX SEQUENCE OF HH3CVoPeerCfgCallerPermitEntry
            MAX-ACCESS not-accessible
            STATUS current
            DESCRIPTION
                "The table contains permitted caller number in the specific
                voice entity for incoming call."
            ::= { hh3cVoPeerObjects 5 }

        hh3cVoPeerCfgCallerPermitEntry OBJECT-TYPE
            SYNTAX HH3CVoPeerCfgCallerPermitEntry
            MAX-ACCESS not-accessible
            STATUS current
            DESCRIPTION
                "The entry of hh3cVoPeerCfgCallerPermitTable."
            INDEX { hh3cVoPeerCfgIndex, hh3cVoPeerCfgCallerPermitNum }
            ::= { hh3cVoPeerCfgCallerPermitTable 1 }

        HH3CVoPeerCfgCallerPermitEntry ::=
            SEQUENCE {
                hh3cVoPeerCfgCallerPermitNum
                    OCTET STRING,
                hh3cVoPeerCallerPermitRowStatus
                    RowStatus
            }

        hh3cVoPeerCfgCallerPermitNum OBJECT-TYPE
            SYNTAX OCTET STRING
            MAX-ACCESS not-accessible
            STATUS current
            DESCRIPTION
                "This object specifies permitted caller number."
            ::= { hh3cVoPeerCfgCallerPermitEntry 1 }

        hh3cVoPeerCallerPermitRowStatus OBJECT-TYPE
            SYNTAX RowStatus
            MAX-ACCESS read-create
            STATUS current
            DESCRIPTION
                "This object is used to create, delete or modify a row
                in this table."
            ::= { hh3cVoPeerCfgCallerPermitEntry 2 }

    END
