-- Copyright (C) 2002 by  HUAWEI TECHNOLOGIES. All rights reserved.
--
-- Description: The purpose of this MIB file is to provide the define of
--              voice general MIB of HUAWEI quidway serial router.
-- Reference:
-- ==========================================================================
HUAWEI-VO-GENERAL-MIB DEFINITIONS ::= BEGIN

	IMPORTS
		OBJECT-TYPE, MODULE-IDENTITY
			FROM SNMPv2-SMI
		voice
			FROM HUAWEI-3COM-OID-MIB;	

		hwVoiceGeneralMIB MODULE-IDENTITY 
			LAST-UPDATED "200410200000Z"		-- Oct 20, 2004  GMT
			ORGANIZATION 
				"Huawei-3COM Technologies Co., Ltd."
			CONTACT-INFO 
				"PLAT Team Huawei 3Com Technologies co.,Ltd.								
				Shang-Di Information Industry Base,
				Hai-Dian District Beijing P.R. China
				http://www.huawei-3com.com
				Zip:100085"
			DESCRIPTION 
				" "
			REVISION "200404081345Z"		-- April 08, 2004 at 13:45 GMT
			DESCRIPTION 
				""
			::= { voice 1 }


EntryStatus ::= INTEGER
                         { valid(1),
                           createRequest(2),
                           underCreation(3),
                           invalid(4)
                         }		
--  The status of a table entry.
-- 
-- Setting this object to the value invalid(4) has the
-- effect of invalidating the corresponding entry.
-- That is, it effectively disassociates the mapping
-- identified with said entry.
-- It is an implementation-specific matter as to whether
-- the agent removes an invalidated entry from the table.
-- Accordingly, management stations must be prepared to
-- receive tabular information from agents that
-- corresponds to entries currently not in use.  Proper
-- interpretation of such entries requires examination
-- of the relevant EntryStatus object.
-- 
-- An existing instance of this object cannot be set to
-- createRequest(2).  This object may only be set to
-- createRequest(2) when this instance is created.  When
-- this object is created, the agent may wish to create
-- supplemental object instances with default values
-- to complete a conceptual row in this table.  Because
-- the creation of these default objects is entirely at
-- the option of the agent, the manager must not assume
-- that any will be created, but may make use of any that
-- are created. Immediately after completing the create
-- operation, the agent must set this object to
-- underCreation(3).
-- 
-- When in the underCreation(3) state, an entry is
-- allowed to exist in a possibly incomplete, possibly
-- inconsistent state, usually to allow it to be
-- modified in mutiple PDUs.  When in this state, an
-- entry is not fully active.  Entries shall exist in
-- the underCreation(3) state until the management
-- station is finished configuring the entry and sets
-- this object to valid(1) or aborts, setting this
-- object to invalid(4).  If the agent determines that
-- an entry has been in the underCreation(3) state for
-- an abnormally long time, it may decide that the
-- management station has crashed.  If the agent makes
-- this decision, it may set this object to invalid(4)
-- to reclaim the entry.  A prudent agent will
-- understand that the management station may need to
-- wait for human input and will allow for that
-- possibility in its determination of this abnormally
-- long period.
-- 
-- An entry in the valid(1) state is fully configured and
-- consistent and fully represents the configuration or
-- operation such a row is intended to represent.  For
-- example, it could be a statistical function that is
-- configured and active, or a filter that is available
-- in the list of filters processed by the packet capture
-- process.
-- 
-- A manager is restricted to changing the state of an
-- entry in the following ways:
-- 
--                       create   under
--      To:       valid  Request  Creation  invalid
-- From:
-- valid             OK       NO        OK       OK
-- createRequest    N/A      N/A       N/A      N/A
-- underCreation     OK       NO        OK       OK
-- invalid           NO       NO        NO       OK
-- nonExistent       NO       OK        NO       OK
-- 
-- In the table above, it is not applicable to move the
-- state from the createRequest state to any other
-- state because the manager will never find the
-- variable in that state.  The nonExistent state is
-- not a value of the enumeration, rather it means that
-- the entryStatus variable does not exist at all.
-- 
-- An agent may allow an entryStatus variable to change
-- state in additional ways, so long as the semantics
-- of the states are followed.  This allowance is made
-- to ease the implementation of the agent and is made
-- despite the fact that managers should never
-- excercise these additional state transitions.

	
--
-- Node definitions
--

		hwVoiceGeneralObjects OBJECT IDENTIFIER ::= { hwVoiceGeneralMIB 1 }

		
		hwVoiceGeneralGroup OBJECT IDENTIFIER ::= { hwVoiceGeneralObjects 1 }

		
--  Voice General Group
-- 
-- The objects in this group specifies the Voice General Configuration
-- information of this gateway .
		hwVoGeneralJitterLen OBJECT-TYPE
			SYNTAX INTEGER (0..10)
			MAX-ACCESS read-write
			STATUS current
			DESCRIPTION
				"This object specifies the length of the Jitter buffer.
				The default value is 3."
			DEFVAL { 3 }
			::= { hwVoiceGeneralGroup 1 }

		
		hwVoGeneralMatchPolicy OBJECT-TYPE
			SYNTAX INTEGER
				{
				long(1),
				short(2)
				}
			MAX-ACCESS read-write
			STATUS current
			DESCRIPTION
				"This object specifies match number policy of this gateway.
				The default value is short."
			DEFVAL { short }
			::= { hwVoiceGeneralGroup 2 }

		
		hwVoGeneralSendPerformance OBJECT-TYPE
			SYNTAX INTEGER
				{
				normal(1),
				fast(2)
				}
			MAX-ACCESS read-write
			STATUS current
			DESCRIPTION
				"This object specifies the performance of sending voice data.
				The default value is normal."
			DEFVAL { normal }
			::= { hwVoiceGeneralGroup 3 }

		
		hwVoGeneralReceivePerformance OBJECT-TYPE
			SYNTAX INTEGER
				{
				normal(1),
				fast(2)
				}
			MAX-ACCESS read-write
			STATUS current
			DESCRIPTION
				"This object specifies the performance of receiving voice data.
				The default value is normal"
			DEFVAL { normal }
			::= { hwVoiceGeneralGroup 4 }

		hwVoGeneralDataStatistics OBJECT-TYPE
			SYNTAX INTEGER
				{
				enable(1),
				disable(2)
				}
			MAX-ACCESS read-write
			STATUS current
			DESCRIPTION
				"Enable/disable data statistics"
			DEFVAL { disable }
			::= { hwVoiceGeneralGroup 5 }

		hwVoGeneralPacketPrecedence OBJECT-TYPE
			SYNTAX INTEGER (0..7)
			MAX-ACCESS read-write
			STATUS current
			DESCRIPTION
				"Set global Voip packet precedence"
			DEFVAL { 0 }
			::= { hwVoiceGeneralGroup 6 }      

		hwVoGeneralDialTerminator OBJECT-TYPE
			SYNTAX OCTET STRING (SIZE (0..1))
			MAX-ACCESS read-write
			STATUS current
			DESCRIPTION
				"Set global Dial Terminator"
			::= { hwVoiceGeneralGroup 7 }

		hwVoGeneralCallStart OBJECT-TYPE
			SYNTAX INTEGER
				{
				fast(1),
				normal(2)
				}
			MAX-ACCESS read-write
			STATUS current
			DESCRIPTION
				"Set the start mode of called over IP" 
			DEFVAL { fast }
			::= { hwVoiceGeneralGroup 8 }

		hwVoGeneralCalledTunnel OBJECT-TYPE
			SYNTAX INTEGER
				{
				enable(1),
				disable(2)
				}
			MAX-ACCESS read-write
			STATUS current
			DESCRIPTION
				"Enable/disable Called tunnel function"
			DEFVAL { enable }
			::= { hwVoiceGeneralGroup 9 }
			
		hwVoGeneralSpecialServiceEnable OBJECT-TYPE
			SYNTAX INTEGER
				{
				enable(1),
				disable(2)
				} 
			MAX-ACCESS read-write    
			STATUS current
			DESCRIPTION
				"This object sepcifies whether special service number
				function is enable or disable." 
			DEFVAL { disable }
			::= { hwVoiceGeneralGroup 10 }
        
        
		hwVoGeneralCallTransferSpecialServiceNumber OBJECT-TYPE
			SYNTAX OCTET STRING(SIZE(1..12))
			MAX-ACCESS read-write    
			STATUS current
			DESCRIPTION
				"This object specifies the call-transfer special service number
			 	in talking."
			DEFVAL { "*12*" }
			::= { hwVoiceGeneralGroup 11 }

        
		hwVoGeneralPeerSearchStop OBJECT-TYPE
			SYNTAX INTEGER(1..200)
			MAX-ACCESS read-write    
			STATUS current
			DESCRIPTION
				"This object specifies the maximum in searching entities."
			DEFVAL { 200 }
			::= { hwVoiceGeneralGroup 12 }

        
		hwVoGeneralPeerSelectOrderRule OBJECT-TYPE
			SYNTAX INTEGER(0..18)
			MAX-ACCESS read-write    
			STATUS current
			DESCRIPTION
				"This object specifies the rule order applied in voice
				entity selection.
				0 --- explicit match, priority, random
				1 --- explicit match, priority, longest no use
				2 --- explicit match, longest no use, priority
				3 --- explicit match, longest no use, random
				4 --- priority, explicit match, random
				5 --- priority, explicit match, longest no usep
				6 --- riority, longest no use, explicit match
				7 --- priority, longest no use, random
				8 --- longest no use, explicit match, priority
				9 --- longest no use, explicit match, random
				10 --- longest no use, priority, explicit match
				11 --- longest no use, priority, random
				12 --- explicit match, random
				13 --- priority, random
				14 --- longest no use, random
				15 --- explicit match
				16 --- priority
				17 --- random
				18 --- longest no use
				"
			DEFVAL { 0 }
			::= { hwVoiceGeneralGroup 13 }

        
		hwVoGeneralPeerSelectTypePriority OBJECT-TYPE
			SYNTAX INTEGER(0..6)
			MAX-ACCESS read-write    
			STATUS current
			DESCRIPTION
				"This object specifies the priority-ranked type of voice entity.
				      1ST  2DN  3RD
				0 --- NONE TYPE
				1 --- VOIP POTS VOFR
				2 --- VOIP VOFR POTS
				3 --- POTS VOIP VOFR
				4 --- POTS VOFR VOIP
				5 --- VOFR POTS VOIP
				6 --- VOFR POTS POTS
				"
			DEFVAL { 0 }
			::= { hwVoiceGeneralGroup 14 }

--  Global Dial Expansion Table
-- 
-- hwVoDialExpansionTable
-- Table to store the Global Dial Expansion information.  
		hwVoDialExpansionTable OBJECT-TYPE
			SYNTAX SEQUENCE OF HWVoDialExpansionEntry
			MAX-ACCESS not-accessible
			STATUS current
			DESCRIPTION
				"The table contains the information of the Dial Expansion Record ."
			::= { hwVoiceGeneralObjects 3 }

		
		hwVoDialExpansionEntry OBJECT-TYPE
			SYNTAX HWVoDialExpansionEntry
			MAX-ACCESS not-accessible
			STATUS current
			DESCRIPTION
				"The information regarding a Dial Expansion Record."
			INDEX { hwVoDialExpansionType,hwVoDialExpansionSource }
			::= { hwVoDialExpansionTable 1 }

		
		HWVoDialExpansionEntry ::=
			SEQUENCE { 
				hwVoDialExpansionType
					INTEGER,
				hwVoDialExpansionSource
					OCTET STRING,
				hwVoDialExpansionTarget
					OCTET STRING,
				hwVoDialExpansionRowStatus
					EntryStatus
			 }

		hwVoDialExpansionType OBJECT-TYPE
			SYNTAX INTEGER
			    {
			        callin(0),
			        callout(1)    
			    }
			MAX-ACCESS read-only
			STATUS current
			DESCRIPTION
				"The call direction of the Dial Expansion. "
			::= { hwVoDialExpansionEntry 1 }

		
		hwVoDialExpansionSource OBJECT-TYPE
			SYNTAX OCTET STRING (SIZE (1..31))
			MAX-ACCESS read-only
			STATUS current
			DESCRIPTION
				"This source telephone of the Dial Expansion.  "
			::= { hwVoDialExpansionEntry 2 }

		hwVoDialExpansionTarget OBJECT-TYPE
			SYNTAX OCTET STRING (SIZE (1..31))
			MAX-ACCESS read-write
			STATUS current
			DESCRIPTION
				"This target telephone of the Dial Expansion.  "
			::= { hwVoDialExpansionEntry 3 }

		
		hwVoDialExpansionRowStatus OBJECT-TYPE
			SYNTAX EntryStatus
			MAX-ACCESS read-write
			STATUS current
			DESCRIPTION
				"This object is used to create a new row or modify or
				delete an existing row in this table. "
			::= { hwVoDialExpansionEntry 4 }

		
--  Voice Logic Channel to Physical Channel Table
-- 
-- hwVoLtoPTable
-- Table to store relation map  between voice logic channel and
-- physical channel. The hwVoLtoPSlot and hwVoLtoPport can indicates a
-- single physical voice channel ,hwVoLtoPChannel indicates a single 
-- logic voice channel, others is some relevated informations .
		hwVoLtoPTable OBJECT-TYPE
			SYNTAX SEQUENCE OF HWVoLtoPEntry
			MAX-ACCESS not-accessible
			STATUS current
			DESCRIPTION
				"The table contains the relation information of Voice logic channel
				and voice physical channel."
			::= { hwVoiceGeneralObjects 2 }

		
		hwVoLtoPEntry OBJECT-TYPE
			SYNTAX HWVoLtoPEntry
			MAX-ACCESS not-accessible
			STATUS current
			DESCRIPTION
				"The information regarding a single logic voice channel ."
			INDEX { hwVoLtoPChannel }
			::= { hwVoLtoPTable 1 }

		
		HWVoLtoPEntry ::=
			SEQUENCE { 
				hwVoLtoPChannel
					INTEGER,
				hwVoLtoPSlot
					INTEGER,
				hwVoLtoPPort
					INTEGER,
				hwVoLtoPTimeSlot
					INTEGER,
				hwVoLtoPStatus
					INTEGER,
				hwVoLtoPBoardType
					INTEGER,
				hwVoLtoPPortNumber
					INTEGER,
				hwVoLtoPGroupNumber
					INTEGER
			 }

		hwVoLtoPChannel OBJECT-TYPE
			SYNTAX INTEGER
			MAX-ACCESS read-only
			STATUS current
			DESCRIPTION
				"The number of this  logic  voice channel  ."
			::= { hwVoLtoPEntry 1 }

		
		hwVoLtoPSlot OBJECT-TYPE
			SYNTAX INTEGER
			MAX-ACCESS read-only
			STATUS current
			DESCRIPTION
				"The physical slot number which this logic voice channel based on."
			::= { hwVoLtoPEntry 2 }

		
		hwVoLtoPPort OBJECT-TYPE
			SYNTAX INTEGER
			MAX-ACCESS read-only
			STATUS current
			DESCRIPTION
				"The physical port number which this logic voice channel based on."
			::= { hwVoLtoPEntry 3 }

		
		hwVoLtoPTimeSlot OBJECT-TYPE
			SYNTAX INTEGER
			MAX-ACCESS read-only
			STATUS current
			DESCRIPTION
				"The timeslots map this logic channel is using .
				-1 represent this channel cann't be used by voice."
			::= { hwVoLtoPEntry 4 }

		
		hwVoLtoPStatus OBJECT-TYPE
			SYNTAX INTEGER
				{
				up(1),
				down(2)
				}
			MAX-ACCESS read-only
			STATUS current
			DESCRIPTION
				"The current  status of the physical voice channel."
			::= { hwVoLtoPEntry 5 }

		
		hwVoLtoPBoardType OBJECT-TYPE
			SYNTAX INTEGER
				{
				fxs2(1),
				fxo2(2),
				em2(3),
				fxs4(4),
				fxo4(5),
				em4(6),
				e1vi(7),
				t1vi(8),
				sic-fxs1(9),
				sic-fxo1(10),
				sic-fxs2(11),
				sic-fxo2(12)
				}
			MAX-ACCESS read-only
			STATUS current
			DESCRIPTION
				"The board type of the physical voice channel."
			::= { hwVoLtoPEntry 6 }

		
		hwVoLtoPPortNumber OBJECT-TYPE
			SYNTAX INTEGER
			MAX-ACCESS read-only
			STATUS current
			DESCRIPTION
				"The global port number of the logic voice channel.
				-1 represent this channel cann't be used by voice."
			::= { hwVoLtoPEntry 7 }

		
		hwVoLtoPGroupNumber OBJECT-TYPE
			SYNTAX INTEGER (-1..30 | 255)
			MAX-ACCESS read-only
			STATUS current
			DESCRIPTION
				"The global group number of the logic voice channel. .
				-1 represent this channel cann't be used by voice ."
			::= { hwVoLtoPEntry 8 }

		
-- Voice Number-substitute Rule Table 
--
-- voNumSubstTable
-- Table to store basic information about number-substitute include
-- dot match rule and the first rule tag that the rule is used firstly.
		hwVoiceNumberSubstGroup OBJECT IDENTIFIER ::= { hwVoiceGeneralObjects 4 }
                             
		hwVoNumSubstTable OBJECT-TYPE
			SYNTAX SEQUENCE OF HWVoNumSubstEntry
			MAX-ACCESS not-accessible
			STATUS current
			DESCRIPTION
				"The table is the number-substitute rule table. It contains
				the table index, dot match rule and the first rule tag that 
				the rule is used firstly."
			::= { hwVoiceNumberSubstGroup 1 }

        
		hwVoNumSubstEntry OBJECT-TYPE
			SYNTAX HWVoNumSubstEntry
			MAX-ACCESS not-accessible
			STATUS current
			DESCRIPTION
 				"A number-substitute rule list. One entry per number-substite
				rule list."
			INDEX { hwVoNumSubstIndex }
			::= { hwVoNumSubstTable 1 }
       
		HWVoNumSubstEntry ::= SEQUENCE
			{
			hwVoNumSubstIndex
				INTEGER,
			hwVoNumSubstFirstRule
 				INTEGER,
			hwVoNumSubstDotMatchRule
				INTEGER,
			hwVoNumSubstRowStatus
				EntryStatus
			}
        

		hwVoNumSubstIndex OBJECT-TYPE
			SYNTAX INTEGER(1..2147483647)
			MAX-ACCESS read-only
			STATUS current
			DESCRIPTION
	            "The index uniquely identifies a number-substitute rule list.
	             It is valid if its value is between 1 and 2147483647."
            ::= { hwVoNumSubstEntry 1 }


		hwVoNumSubstFirstRule  OBJECT-TYPE
			SYNTAX INTEGER(0..127|65535)
			MAX-ACCESS read-write
			STATUS current
			DESCRIPTION
	            "This object specifies the first rule to be used firstly.
                 It is valid if its value is between 0 and 127."
	        DEFVAL { 65535 }
            ::= { hwVoNumSubstEntry 2 }

        
		hwVoNumSubstDotMatchRule  OBJECT-TYPE
			SYNTAX INTEGER
				{
				end-only(1),
				left-right(2),
				right-left(3)
				}
			MAX-ACCESS read-write
			STATUS current
			DESCRIPTION
				"This object specifies the dot wildcard match rule.
				end-only   - only end of E.164 number (input format)
				left-right - match form left to right (input format)
				right-left - match form right to left (input format)
				"
			DEFVAL { 1 }
			::= { hwVoNumSubstEntry 3 }
        
        
		hwVoNumSubstRowStatus OBJECT-TYPE
			SYNTAX EntryStatus
			MAX-ACCESS read-write
			STATUS current
			DESCRIPTION
				"This object is used to create a new row or modify or
				delete an existing row in this table."
			::= { hwVoNumSubstEntry 4 }

 
-- Voice Number-substitute Rule Table 
-- 
-- voNumSubstRuleTable
-- Table to store relation map between before-substituting number and 
-- after-substituting number. Before-substituting number and after-substituting
-- indicate a substituting rule about number.
		hwVoNumSubstRuleTable OBJECT-TYPE
			SYNTAX SEQUENCE OF HWVoNumSubstRuleEntry
			MAX-ACCESS not-accessible
			STATUS current
			DESCRIPTION
				"The table contains the number-substitute rule information 
				that is used to create an rule row with an appropriate
				rule index."
			::= { hwVoiceNumberSubstGroup 2 }
        
        	hwVoNumSubstRuleEntry OBJECT-TYPE
			SYNTAX HWVoNumSubstRuleEntry
			MAX-ACCESS not-accessible
			STATUS current
			DESCRIPTION
				"A single number-substitute rule. One entry per 
				number-substitute rule."
			INDEX { hwVoNumSubstIndex,hwVoNumSubstRuleIndex }
			::= { hwVoNumSubstRuleTable 1 }

		HWVoNumSubstRuleEntry ::= 
			SEQUENCE{
				hwVoNumSubstRuleIndex
					INTEGER,
				hwVoNumSubstRuleInputFormat
					OCTET STRING,
				hwVoNumSubstRuleOutputFormat
					OCTET STRING,
				hwVoNumSubstRuleRowStatus
					EntryStatus
			}
        
        
        	hwVoNumSubstRuleIndex OBJECT-TYPE
			SYNTAX INTEGER(0..127)
			MAX-ACCESS read-only
			STATUS current
			DESCRIPTION
				"The index uniquely identifies a number-substitute rule.
				It is valid if its value is between 0 and 127."
			::= { hwVoNumSubstRuleEntry 1 }
        
        
        	hwVoNumSubstRuleInputFormat OBJECT-TYPE
			SYNTAX OCTET STRING(SIZE(1..31))
			MAX-ACCESS read-write
			STATUS current
			DESCRIPTION
				"This object specifies the input match format that must
				be of the form ^(\^)!(\+)!([0-9ABCD.*%!#]+)(\$)!$."
			::= { hwVoNumSubstRuleEntry 2 }
        
        
        	hwVoNumSubstRuleOutputFormat OBJECT-TYPE
			SYNTAX OCTET STRING(SIZE(1..31))
			MAX-ACCESS read-write
			STATUS current
			DESCRIPTION
				"This object specifies the output format that must
				be of the form ^[0-9#.]+$."
			::= { hwVoNumSubstRuleEntry 3 }
                       
        
        	hwVoNumSubstRuleRowStatus OBJECT-TYPE
			SYNTAX EntryStatus
			MAX-ACCESS read-write
			STATUS current
			DESCRIPTION
				"This object is used to create a new row or modify or
				delete an existing row in this table."
			::= { hwVoNumSubstRuleEntry 4 }


-- Voice Maximum call Table
--
-- voMaxCallTable
-- Table to store the maximum number of allowed connections for a set of 
-- voice entities.
        	hwVoMaxCallTable OBJECT-TYPE
			SYNTAX SEQUENCE OF HWVoMaxCallEntry
			MAX-ACCESS not-accessible    
			STATUS current
			DESCRIPTION
				"The table stores The table stores the maximum number of allowed 
				connections for a set of voice entities."
			::= { hwVoiceGeneralObjects 5 }
        
        
        	hwVoMaxCallEntry OBJECT-TYPE
			SYNTAX HWVoMaxCallEntry
			MAX-ACCESS not-accessible
			STATUS current
			DESCRIPTION
				"A single value of maximum call connections. One entry per 
				maximum call connections." 
			INDEX { hwVoMaxCallTableIndex }
			::= { hwVoMaxCallTable 1 }
      
		HWVoMaxCallEntry ::= 
			SEQUENCE {
				hwVoMaxCallTableIndex
					INTEGER,
				hwVoMaxCallValue
					INTEGER,
				hwVoMaxCallTableRowStatus
					EntryStatus
			}
              
        
		hwVoMaxCallTableIndex OBJECT-TYPE
			SYNTAX INTEGER(1..2147483647)
			MAX-ACCESS read-only    
			STATUS current
			DESCRIPTION
				"The index uniquely identifies a single maximum call value.
				It is valid if its value is between 1 and 2147483647."
			::= { hwVoMaxCallEntry 1 }
        
        
        	hwVoMaxCallValue OBJECT-TYPE      
			SYNTAX INTEGER(0..120)
			MAX-ACCESS read-write    
			STATUS current
			DESCRIPTION
				"This object specifies a single maximum call value.
				It is valid if its value is between 0 and 120."
			::= { hwVoMaxCallEntry 2 }
        
        
        	hwVoMaxCallTableRowStatus OBJECT-TYPE
			SYNTAX EntryStatus
			MAX-ACCESS read-write
			STATUS current
			DESCRIPTION
				"This object is used to create a new row or modify or
				delete an existing row in this table."
			::= { hwVoMaxCallEntry 3 }
            
        
--  
-- Incoming-call Calling Number Number-substitute Rule Table 
--
        	hwVoIncomingCallingNumSubstTable OBJECT-TYPE
			SYNTAX SEQUENCE OF HWVoIncomingCallingNumSubstEntry
			MAX-ACCESS not-accessible
			STATUS current
			DESCRIPTION
				"The table stores the number-substitute rule list tag that these
				number-substitute rule list will be used for incoming-call caller
				number.The table can hold max 32 rows."
			::= { hwVoiceGeneralObjects 6 }
        
                
        	hwVoIncomingCallingNumSubstEntry OBJECT-TYPE
			SYNTAX HWVoIncomingCallingNumSubstEntry
			MAX-ACCESS not-accessible
			STATUS current
			DESCRIPTION
				"A number-substitute rule list tag. One entry per number-substite
				rule list tag."
			INDEX { hwVoIncomingCallingNumSubstIndex }
			::= { hwVoIncomingCallingNumSubstTable 1 }
       
		HWVoIncomingCallingNumSubstEntry ::= 
			SEQUENCE {
				hwVoIncomingCallingNumSubstIndex
					INTEGER,
				hwVoIncomingCallingNumSubstRowStatus
					EntryStatus
			}
        
        
        	hwVoIncomingCallingNumSubstIndex OBJECT-TYPE
			SYNTAX INTEGER(1..2147483647)
			MAX-ACCESS read-only
			STATUS current
			DESCRIPTION
				"This object specifies a number-substitute rule that apply caller
				number for incoming call. It is valid if its value is between 1
				and 2147483647."
			::= { hwVoIncomingCallingNumSubstEntry 1 }
        
        
        	hwVoIncomingCallingNumSubstRowStatus OBJECT-TYPE
			SYNTAX EntryStatus
			MAX-ACCESS read-write
			STATUS current
			DESCRIPTION
				"This object is used to create a new row or modify or
				delete an existing row in this table."
			::= { hwVoIncomingCallingNumSubstEntry 2 }


--  
-- Incoming-call Called Number Number-substitute Rule Table 
--
        	hwVoIncomingCalledNumSubstTable OBJECT-TYPE
			SYNTAX SEQUENCE OF HWVoIncomingCalledNumSubstEntry
			MAX-ACCESS not-accessible
			STATUS current
			DESCRIPTION
				"The table stores the number-substitute rule list tag that these
				number-substitute rule list will be used for incoming-call caller
				number.The table can hold max 32 rows."
		::= { hwVoiceGeneralObjects 7 }
        
                
        	hwVoIncomingCalledNumSubstEntry OBJECT-TYPE
			SYNTAX HWVoIncomingCalledNumSubstEntry
			MAX-ACCESS not-accessible
			STATUS current
			DESCRIPTION
				"A number-substitute rule list tag. One entry per number-substite
				rule list tag."
			INDEX { hwVoIncomingCalledNumSubstIndex }
			::= { hwVoIncomingCalledNumSubstTable 1 }
       
		HWVoIncomingCalledNumSubstEntry ::= 
			SEQUENCE {
				hwVoIncomingCalledNumSubstIndex
					INTEGER,
				hwVoIncomingCalledNumSubstRowStatus
					EntryStatus
			}
        
        
		hwVoIncomingCalledNumSubstIndex OBJECT-TYPE
			SYNTAX INTEGER(1..2147483647)
			MAX-ACCESS read-only
			STATUS current
			DESCRIPTION
				"This object specifies a number-substitute rule that apply caller
				number for incoming call. It is valid if its value is between 1
				and 2147483647."
			::= { hwVoIncomingCalledNumSubstEntry 1 }
        
        
        	hwVoIncomingCalledNumSubstRowStatus OBJECT-TYPE
			SYNTAX EntryStatus
			MAX-ACCESS read-write
			STATUS current
			DESCRIPTION
				"This object is used to create a new row or modify or
				delete an existing row in this table."
			::= { hwVoIncomingCalledNumSubstEntry 2 }
            

--  
-- Incoming-call Calling Number Number-substitute Rule Table 
--
        	hwVoOutgoingCallingNumSubstTable OBJECT-TYPE
			SYNTAX SEQUENCE OF HWVoOutgoingCallingNumSubstEntry
			MAX-ACCESS not-accessible
			STATUS current
			DESCRIPTION
				"The table stores the number-substitute rule list tag that these
				number-substitute rule list will be used for incoming-call caller
				number.The table can hold max 32 rows."
			::= { hwVoiceGeneralObjects 8 }
        
                
        	hwVoOutgoingCallingNumSubstEntry OBJECT-TYPE
			SYNTAX HWVoOutgoingCallingNumSubstEntry
			MAX-ACCESS not-accessible
			STATUS current
			DESCRIPTION
				"A number-substitute rule list tag. One entry per number-substite
				rule list tag."
			INDEX { hwVoOutgoingCallingNumSubstIndex }
			::= { hwVoOutgoingCallingNumSubstTable 1 }

       
		HWVoOutgoingCallingNumSubstEntry ::= 
			SEQUENCE {
				hwVoOutgoingCallingNumSubstIndex
					INTEGER,
				hwVoOutgoingCallingNumSubstRowStatus
					EntryStatus
			}
        
        
        	hwVoOutgoingCallingNumSubstIndex OBJECT-TYPE
			SYNTAX INTEGER(1..2147483647)
			MAX-ACCESS read-only
			STATUS current
			DESCRIPTION
				"This object specifies a number-substitute rule that apply caller
				number for incoming call. It is valid if its value is between 1
				and 2147483647."
			::= { hwVoOutgoingCallingNumSubstEntry 1 }
        
        
        	hwVoOutgoingCallingNumSubstRowStatus OBJECT-TYPE
			SYNTAX EntryStatus
			MAX-ACCESS read-write
			STATUS current
			DESCRIPTION
				"This object is used to create a new row or modify or
				delete an existing row in this table."
			::= { hwVoOutgoingCallingNumSubstEntry 2 }


            
--  
-- Outgoing-call Calling Number Number-substitute Rule Table 
--
        	hwVoOutgoingCalledNumSubstTable OBJECT-TYPE
			SYNTAX SEQUENCE OF HWVoOutgoingCalledNumSubstEntry
			MAX-ACCESS not-accessible
			STATUS current
			DESCRIPTION
				"The table stores the number-substitute rule list tag that these
				number-substitute rule list will be used for incoming-call caller
				number.The table can hold max 32 rows."
			::= { hwVoiceGeneralObjects 9 }
        
                
        	hwVoOutgoingCalledNumSubstEntry OBJECT-TYPE
			SYNTAX HWVoOutgoingCalledNumSubstEntry
			MAX-ACCESS not-accessible
			STATUS current
			DESCRIPTION
				"A number-substitute rule list tag. One entry per number-substite
				rule list tag."
			INDEX { hwVoOutgoingCalledNumSubstIndex }
			::= { hwVoOutgoingCalledNumSubstTable 1 }
       
        	HWVoOutgoingCalledNumSubstEntry ::= 
			SEQUENCE {
				hwVoOutgoingCalledNumSubstIndex
					INTEGER,
				hwVoOutgoingCalledNumSubstRowStatus
					EntryStatus
			}
        
        
        	hwVoOutgoingCalledNumSubstIndex OBJECT-TYPE
			SYNTAX INTEGER(1..2147483647)
			MAX-ACCESS read-only
			STATUS current
			DESCRIPTION
				"This object specifies a number-substitute rule that apply caller
				number for incoming call. It is valid if its value is between 1
				and 2147483647."
			::= { hwVoOutgoingCalledNumSubstEntry 1 }
        
        
		hwVoOutgoingCalledNumSubstRowStatus OBJECT-TYPE
			SYNTAX EntryStatus
			MAX-ACCESS read-write
			STATUS current
			DESCRIPTION
				"This object is used to create a new row or modify or
				delete an existing row in this table."
			::= { hwVoOutgoingCalledNumSubstEntry 2 }
	
	END
