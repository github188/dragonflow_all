-- ==========================================================================
-- Copyright (C) 2004 by Huawei 3Com Technologies. All rights reserved.
--
-- Description: The purpose of this MIB file is to provide the definition of
--              the message statistic information MIB of H323.
-- Reference:
-- ==========================================================================
H3C-VOH323CALLSTAT-MIB DEFINITIONS ::= BEGIN
    IMPORTS
        OBJECT-TYPE, MODULE-IDENTITY, Counter32, Integer32
            FROM SNMPv2-SMI
        h3cVoice
            FROM HUAWEI-3COM-OID-MIB;   
    
    
        h3cVoiceH323CallStat MODULE-IDENTITY 
            LAST-UPDATED "200503150000Z"
            ORGANIZATION 
                "Huawei-3COM Technologies Co., Ltd."
            CONTACT-INFO 
                "PLAT Team Huawei 3Com Technologies co.,Ltd.                                
                Shang-Di Information Industry Base,
                Hai-Dian District Beijing P.R. China
                http://www.huawei-3com.com
                Zip:100085"
            DESCRIPTION 
                "This MIB is to provide the definition of the message 
                statistic information MIB of H323."
            REVISION "200503150000Z"
            DESCRIPTION 
                "The initial version of this MIB file."
            ::= { h3cVoice 11 }
        


--===========================================================================
--                h3cVOIPH225StatTable

--===========================================================================
        h3cVOIPH225StatTable OBJECT-TYPE
            SYNTAX SEQUENCE OF H3CVOIPH225StatEntry
            MAX-ACCESS not-accessible
            STATUS current
            DESCRIPTION
                "A list of voip H225 message statistics entries."
            ::= { h3cVoiceH323CallStat 1 }
    
    
        h3cVOIPH225StatEntry OBJECT-TYPE
            SYNTAX H3CVOIPH225StatEntry
            MAX-ACCESS not-accessible
            STATUS current
            DESCRIPTION
                "A collection of statistics kept for a H225 message."
            INDEX { h3cH225MsgIndex }
            ::= { h3cVOIPH225StatTable 1 }
    
        H3CVOIPH225StatEntry ::=
            SEQUENCE {
                h3cH225MsgIndex
                    Integer32,
                h3cH225MsgName
                    OCTET STRING,    
                h3cH225MsgSend
                    Counter32,
                h3cH225MsgReceive
                    Counter32
                }
    
        h3cH225MsgIndex OBJECT-TYPE
            SYNTAX Integer32
            MAX-ACCESS not-accessible
            STATUS current
            DESCRIPTION
                "The index of a H225 message."
            ::= { h3cVOIPH225StatEntry 1 }
            
        h3cH225MsgName OBJECT-TYPE
            SYNTAX OCTET STRING
            MAX-ACCESS read-only
            STATUS current
            DESCRIPTION
                "The name of a H225 message."
            ::= { h3cVOIPH225StatEntry 2 }
    
        h3cH225MsgSend OBJECT-TYPE
            SYNTAX Counter32
            MAX-ACCESS read-only
            STATUS current
            DESCRIPTION
                "The number of messages which a gateway has sent."
            ::= { h3cVOIPH225StatEntry 3 }
    
    
        h3cH225MsgReceive OBJECT-TYPE
            SYNTAX Counter32
            MAX-ACCESS read-only
            STATUS current
            DESCRIPTION
                "The number of messages which a gateway has received."
            ::= { h3cVOIPH225StatEntry 4 }
    
            
--===========================================================================
--                h3cVOIPH245StatTable

--===========================================================================
        h3cVOIPH245StatTable OBJECT-TYPE
            SYNTAX SEQUENCE OF H3CVOIPH245StatEntry
            MAX-ACCESS not-accessible
            STATUS current
            DESCRIPTION
                "A list of voip H245 message statistics entries."
            ::= { h3cVoiceH323CallStat 2 }
    
    
        h3cVOIPH245StatEntry OBJECT-TYPE
            SYNTAX H3CVOIPH245StatEntry
            MAX-ACCESS not-accessible
            STATUS current
            DESCRIPTION
                "A collection of statistics kept for a H245
                message. "
            INDEX { h3cH245MsgIndex }
            ::= { h3cVOIPH245StatTable 1 }
    
        H3CVOIPH245StatEntry ::=
            SEQUENCE {
                h3cH245MsgIndex
                    Integer32,
                h3cH245MsgName
                    OCTET STRING,    
                h3cH245MsgSend
                    Counter32,
                h3cH245MsgReceive
                    Counter32
                }
    
        h3cH245MsgIndex OBJECT-TYPE
            SYNTAX Integer32
            MAX-ACCESS not-accessible
            STATUS current
            DESCRIPTION
                "The index of a H245 message."
            ::= { h3cVOIPH245StatEntry 1 }
            
        h3cH245MsgName OBJECT-TYPE
            SYNTAX OCTET STRING
            MAX-ACCESS read-only
            STATUS current
            DESCRIPTION
                "The name of a H245 message."
            ::= { h3cVOIPH245StatEntry 2 }
    
        h3cH245MsgSend OBJECT-TYPE
            SYNTAX Counter32
            MAX-ACCESS read-only
            STATUS current
            DESCRIPTION
                "The number of messages which a gateway has sent."
            ::= { h3cVOIPH245StatEntry 3 }
    
    
        h3cH245MsgReceive OBJECT-TYPE
            SYNTAX Counter32
            MAX-ACCESS read-only
            STATUS current
            DESCRIPTION
                "The number of messages which a gateway has received."
            ::= { h3cVOIPH245StatEntry 4 }

--===========================================================================
--                h3cVOIPRasStatTable

--===========================================================================
        h3cVOIPRasStatTable OBJECT-TYPE
            SYNTAX SEQUENCE OF H3CVOIPHRasStatEntry
            MAX-ACCESS not-accessible
            STATUS current
            DESCRIPTION
                "A list of voip ras message statistics entries."
            ::= { h3cVoiceH323CallStat 3 }
    
    
        h3cVOIPRasStatEntry OBJECT-TYPE
            SYNTAX H3CVOIPHRasStatEntry
            MAX-ACCESS not-accessible
            STATUS current
            DESCRIPTION
                "A collection of statistics kept for a ras
                message. "
            INDEX { h3cRasMsgIndex }
            ::= { h3cVOIPRasStatTable 1 }
    
        H3CVOIPHRasStatEntry ::=
            SEQUENCE {
                h3cRasMsgIndex
                    Integer32,
                h3cRasMsgName
                    OCTET STRING,    
                h3cRasMsgSend
                    Counter32,
                h3cRasMsgReceive
                    Counter32
                }
    
        h3cRasMsgIndex OBJECT-TYPE
            SYNTAX Integer32
            MAX-ACCESS not-accessible
            STATUS current
            DESCRIPTION
                "The index of a ras message."
            ::= { h3cVOIPRasStatEntry 1 }
            
        h3cRasMsgName OBJECT-TYPE
            SYNTAX OCTET STRING
            MAX-ACCESS read-only
            STATUS current
            DESCRIPTION
                "The name of a ras message."
            ::= { h3cVOIPRasStatEntry 2 }
    
        h3cRasMsgSend OBJECT-TYPE
            SYNTAX Counter32
            MAX-ACCESS read-only
            STATUS current
            DESCRIPTION
                "The number of messages which a gateway has sent."
            ::= { h3cVOIPRasStatEntry 3 }
    
    
        h3cRasMsgReceive OBJECT-TYPE
            SYNTAX Counter32
            MAX-ACCESS read-only
            STATUS current
            DESCRIPTION
                "The number of messages which a gateway has received."
            ::= { h3cVOIPRasStatEntry 4 }
        
    
    END
