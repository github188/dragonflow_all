-- ==========================================================================
-- Copyright (C) 2002 by  HUAWEI TECHNOLOGIES. All rights reserved.
--
-- Description: The purpose of this MIB file is to provide the define of
--              the voice interface general configuration MIB of HUAWEI 
--              quidway serial router.
-- Reference:
-- ==========================================================================
HUAWEI-VO-IF-MIB DEFINITIONS ::= BEGIN
 
		IMPORTS
			OBJECT-TYPE, MODULE-IDENTITY
				FROM SNMPv2-SMI
			voice			
				FROM HUAWEI-3COM-OID-MIB;
		
		hwVoiceIfMIB MODULE-IDENTITY 
			LAST-UPDATED "200410200000Z"		-- Oct 20, 2004  GMT
			ORGANIZATION 
				"Huawei-3COM Technologies Co., Ltd."
			CONTACT-INFO 
				"PLAT Team Huawei 3Com Technologies co.,Ltd.								
				Shang-Di Information Industry Base,
				Hai-Dian District Beijing P.R. China
				http://www.huawei-3com.com
				Zip:100085"
			DESCRIPTION 
				" "
			REVISION "200404081345Z"		-- April 08, 2004 at 13:45 GMT
			DESCRIPTION 
				""
			::= { voice 2 }

		
		hwVoIfObjects OBJECT IDENTIFIER ::= { hwVoiceIfMIB 1 }

		
--  The Voice Interface General Configuration Group
-- The Voice Interface General Configuration Table
		hwVoIfConfigTable OBJECT-TYPE
			SYNTAX SEQUENCE OF HWVoIfConfigEntry
			MAX-ACCESS not-accessible
			STATUS current
			DESCRIPTION
				"The voice interface general configuration table contains information
				about configuration parameters for both analog voice interface and 
				digital voice interface."
			::= { hwVoIfObjects 1 }

		
		hwVoIfConfigEntry OBJECT-TYPE
			SYNTAX HWVoIfConfigEntry
			MAX-ACCESS not-accessible
			STATUS current
			DESCRIPTION
				"An entry in the voice interface general configuration table. 
				The entry is automatically created when a voice interface hardware is found."
			INDEX { hwVoIfConfigPortNumber, hwVoIfConfigGroupNumber }
			::= { hwVoIfConfigTable 1 }

		
		HWVoIfConfigEntry ::=
			SEQUENCE { 
				hwVoIfConfigPortNumber
					INTEGER,
				hwVoIfConfigGroupNumber
					INTEGER,
				hwVoIfConfigCngOn
					INTEGER,
				hwVoIfConfigNonLinearProcessSwitch
					INTEGER,
				hwVoIfConfigMusicThreshold
					INTEGER,
				hwVoIfConfigInputGain
					INTEGER,
				hwVoIfConfigOutputGain
					INTEGER,
				hwVoIfConfigEchoCancellationSwitch
					INTEGER,
				hwVoIfConfigEchoCancellationCoverage
					INTEGER,
				hwVoIfConfigEchoCancellationDelay
					INTEGER,
				hwVoIfConfigPlarNumber
					OCTET STRING,
				hwVoIfConfigRegionalTone
					OCTET STRING,
				hwVoIfConfigDescription
					OCTET STRING,
				hwVoIfConfigStatus
					INTEGER,
				hwVoIfConfigDtmfThreshold
					INTEGER,
				hwVoIfConfigCallingNumSubstRule
					INTEGER,
				hwVoIfConfigCalledNumSubstRule
					INTEGER
			 }

		hwVoIfConfigPortNumber OBJECT-TYPE
			SYNTAX INTEGER
			MAX-ACCESS read-only
			STATUS current
			DESCRIPTION
				"Index of voice interface general config table. It identify the  
				number of the voice port."
			::= { hwVoIfConfigEntry 1 }

		
		hwVoIfConfigGroupNumber OBJECT-TYPE
			SYNTAX INTEGER
			MAX-ACCESS read-only
			STATUS current
			DESCRIPTION
				"Index of voice interface general config table. It identify the
				number of the ds0 or pri group. If it is used in an analog interface,
				the value is 255."
			::= { hwVoIfConfigEntry 2 }

		
		hwVoIfConfigCngOn OBJECT-TYPE
			SYNTAX INTEGER
				{
				enable(1),
				disable(2)
				}
			MAX-ACCESS read-write
			STATUS current
			DESCRIPTION
				"This object expresses whether or not the silence gaps should be 
				filled with background noise. The default value is enable."
			DEFVAL { enable }
			::= { hwVoIfConfigEntry 3 }

		
		hwVoIfConfigNonLinearProcessSwitch OBJECT-TYPE
			SYNTAX INTEGER
				{
				enable(1),
				disable(2)
				}
			MAX-ACCESS read-write
			STATUS obsolete
			DESCRIPTION
				"This object expresses the nonlinear processing is enable or disable 
				for the voice interface. The default value is enable."
			DEFVAL { enable }
			::= { hwVoIfConfigEntry 4 }

		
		hwVoIfConfigMusicThreshold OBJECT-TYPE
			SYNTAX INTEGER (-70..-30)
			MAX-ACCESS read-write
			STATUS obsolete
			DESCRIPTION
				"This object states the music threshold of the voice interface.
				The default value is -38 dBm."
			DEFVAL { -38 }
			::= { hwVoIfConfigEntry 5 }

		
		hwVoIfConfigInputGain OBJECT-TYPE
			SYNTAX INTEGER (-14..14)
			MAX-ACCESS read-write
			STATUS current
			DESCRIPTION
				"This object states the amount of gain added to the receive side 
				of the voice interface. The default value is 0 decibel.
				"
			DEFVAL { 0 }
			::= { hwVoIfConfigEntry 6 }

		
		hwVoIfConfigOutputGain OBJECT-TYPE
			SYNTAX INTEGER (-14..14)
			MAX-ACCESS read-write
			STATUS current
			DESCRIPTION
				"This object states the amount of gain added to the send side 
				of the voice interface. The default value is 0 decibel."
			DEFVAL { 0 }
			::= { hwVoIfConfigEntry 7 }

		
		hwVoIfConfigEchoCancellationSwitch OBJECT-TYPE
			SYNTAX INTEGER
				{
				enable(1),
				disable(2)
				}
			MAX-ACCESS read-write
			STATUS current
			DESCRIPTION
				"This object expresses the echo cancellation is enable or disable 
				for the voice interface. The default value is enable."
			DEFVAL { enable }
			::= { hwVoIfConfigEntry 8 }

		
		hwVoIfConfigEchoCancellationCoverage OBJECT-TYPE
			SYNTAX INTEGER
				{
				echoCancelCoverage16ms(1),
				echoCancelCoverage24ms(2),
				echoCancelCoverage32ms(3)
				}
			MAX-ACCESS read-write
			STATUS obsolete
			DESCRIPTION
				"This object states the milliseconds of echo cancellation coverage 
				for the voice interface. This object can only be used when 
				hwVoIfConfigEchoCancellationSwitch is enable. The default value 
				is echoCancelCoverage16ms."
			DEFVAL { echoCancelCoverage16ms }
			::= { hwVoIfConfigEntry 9 }

		
		hwVoIfConfigEchoCancellationDelay OBJECT-TYPE
			SYNTAX INTEGER (0..64)
			MAX-ACCESS read-write
			STATUS current
			DESCRIPTION
				"This object states the delay of the echo cancellation for the voice
				interface. This object can only be used when hwVoIfConfigEchoCancellationSwitch 
				is enable. The default value is 32 milliseconds."
			DEFVAL { 32 }
			::= { hwVoIfConfigEntry 10 }

		
		hwVoIfConfigPlarNumber OBJECT-TYPE
			SYNTAX OCTET STRING (SIZE (0..31))
			MAX-ACCESS read-write
			STATUS current
			DESCRIPTION
				"This object states the E.164 phone number for connection plar mode."
			::= { hwVoIfConfigEntry 11 }

		
		hwVoIfConfigRegionalTone OBJECT-TYPE
			SYNTAX OCTET STRING (SIZE (0 | 2))
			MAX-ACCESS read-only
			STATUS current
			DESCRIPTION
				"This object uses 2 letter country code specify voice parameters of 
				different countrys."
			::= { hwVoIfConfigEntry 12 }

		
		hwVoIfConfigDescription OBJECT-TYPE
			SYNTAX OCTET STRING (SIZE (0..255))
			MAX-ACCESS read-write
			STATUS current
			DESCRIPTION
				"This object contains the description of voice interface"
			::= { hwVoIfConfigEntry 13 }

		
		hwVoIfConfigStatus OBJECT-TYPE
			SYNTAX INTEGER
				{
				up(1),
				down(2)
				}
			MAX-ACCESS read-only
			STATUS current
			DESCRIPTION
				"This object expresses the status of voice interface."
			::= { hwVoIfConfigEntry 14 }

		
		hwVoIfConfigDtmfThreshold OBJECT-TYPE
			SYNTAX INTEGER
				{
				sensitivity(1),
				insensitivty(2)
				}
			MAX-ACCESS read-write
			STATUS current
			DESCRIPTION
				"This object Set the level threshold of recieve DTMF."
			DEFVAL { insensitivty }
			::= { hwVoIfConfigEntry 15 }

		hwVoIfConfigCallingNumSubstRule OBJECT-TYPE          
			SYNTAX INTEGER(0..2147483647)
			MAX-ACCESS read-write
			STATUS current
			DESCRIPTION
				"This object specifies a number-substitute rule that apply calling
				numbor this subscriber line. It is valid if its value is between 1
				and 21474836This subscriber line doesn't apply any number-substitute
				rule if its value is 0.
				"
			DEFVAL     { 0 }
			::= { hwVoIfConfigEntry 16 }
                
		hwVoIfConfigCalledNumSubstRule OBJECT-TYPE          
			SYNTAX INTEGER(0..2147483647)
			MAX-ACCESS read-write
			STATUS current
			DESCRIPTION
				"This object specifies a number-substitute rule that apply called
				number for this subscriber line. It is valid if its value is between 1
				and 2147483647. This subscriber line doesn't apply any number-substitute
				rule if its value is 0.
				"
			DEFVAL     { 0 }
			::= { hwVoIfConfigEntry 17 }  
	
	END
