-- =================================================================
-- Copyright (C) 2001,2002 by  H3C TECHNOLOGIES. All rights reserved.
--
-- Description: description of entity extend properties for H3C products
-- Reference:
-- =================================================================
HH3C-ENTITY-EXT-MIB DEFINITIONS ::= BEGIN

    IMPORTS
        hh3cCommon
            FROM HH3C-OID-MIB
        OBJECT-GROUP, MODULE-COMPLIANCE, NOTIFICATION-GROUP
            FROM SNMPv2-CONF
        OBJECT-TYPE, MODULE-IDENTITY, NOTIFICATION-TYPE, Integer32,
        Unsigned32, Gauge32
            FROM SNMPv2-SMI
        TEXTUAL-CONVENTION, MacAddress
            FROM SNMPv2-TC
        SnmpAdminString
            FROM SNMP-FRAMEWORK-MIB
        entPhysicalName
            FROM ENTITY-MIB;

    hh3cEntityExtend MODULE-IDENTITY
        LAST-UPDATED "200607030000Z"      -- JULY 03, 2006 at 00:00 GMT
        ORGANIZATION
            "Hangzhou H3C Tech. Co., Ltd."
        CONTACT-INFO
            "Platform Team Hangzhou H3C Tech. Co., Ltd.
            Hai-Dian District Beijing P.R. China
            http://www.h3c.com
            Zip:100085
            "
        DESCRIPTION
            "The private MIB file includes the general extent
            information of the device."
        ::= { hh3cCommon 6 }

    Hh3cAdminState  ::=  TEXTUAL-CONVENTION
        STATUS            current
        DESCRIPTION
            "The administrative state for this object, and it is possible to
            set the state when needed.
            A value of locked means the resource is administratively prohibited
            from use. A value of shuttingDown means that usage is
            administratively limited to current instances of use.
            A value of unlocked means the resource is not administratively
            prohibited from use."
        REFERENCE
            "ITU Recommendation X.731, 'Information Technology - Open
            Systems Interconnection - System Management: State
            Management Function', 1992"
        SYNTAX  INTEGER
        {
            notSupported(1),
            locked(2),
            shuttingDown(3),
            unlocked(4)
        }

    Hh3cOperState  ::=  TEXTUAL-CONVENTION
        STATUS            current
        DESCRIPTION
            " Represents the possible values of operational states.
            A value of disabled means the resource is totally
            inoperable. A value of enabled means the resource
            is partially or fully operable."
        REFERENCE
            "ITU Recommendation X.731, 'Information Technology - Open
            Systems Interconnection - System Management: State
            Management Function', 1992"
        SYNTAX  INTEGER
        {
            notSupported (1),
            disabled(2),
            enabled(3),
            dangerous(4)
        }
    Hh3cAlarmStatus  ::=  TEXTUAL-CONVENTION
        STATUS            current
        DESCRIPTION
            "Represents the possible values of alarm status.
            When no bits of this attribute are set, then none of the
            status conditions described below are present. When the
            value of under repair is set, the resource is currently
            being repaired.

            When the value of critical is set, one or more critical
            alarms are active against the resource. When the value of
            major is set, one or more major alarms are active against
            the resource. When the value of minor is set, one or more
            minor alarms are active against the resource. When the
            value of warning is set, one or more warning alarms are
            active against the resource. When the value of
            indeterminate is set, one or more  alarms of indeterminate
            severity are active against the resource.
            When the value of alarm outstanding is set, one or more
            alarms is active against the resource. The fault may or may
            not be disabling."
            REFERENCE
            "ITU Recommendation X.731, 'Information Technology - Open
            Systems Interconnection - System Management: State
            Management Function', 1992"
        SYNTAX           BITS
        {
            notSupported (0),
            underRepair(1),
            critical(2),
            major(3),
            minor(4),
            alarmOutstanding(5),
            warning (6), -- Not defined in X.731
            indeterminate (7) -- Not defined in X.731
        }


    Hh3cStandbyStatus  ::=  TEXTUAL-CONVENTION
        STATUS            current
        DESCRIPTION
                " Represents the possible values of standby status.

                  A value of hotStandby means the resource is not providing
                  service, but is will be immediately able to take over the
                  role of the resource to be backed-up, without the need for
                  initialization activity, and will contain the same
                  information as the resource to be backed up. A value of
                  coldStandy means that the resource is to back-up another
                  resource, but will not be immediately able to take over
                  the role of a resource to be backed up, and will require
                  some initialization activity. A value of providingService
                  means the resource is providing service."
        REFERENCE
            "ITU Recommendation X.731, 'Information Technology - Open
            Systems Interconnection - System Management: State
            Management Function', 1992"
        SYNTAX            INTEGER
        {
            notSupported (1),
            hotStandby(2),
            coldStandby(3),
            providingService(4)
        }


    hh3cEntityExtObjects OBJECT IDENTIFIER ::= { hh3cEntityExtend 1 }


--  MIB contains four groups

    hh3cEntityExtState OBJECT IDENTIFIER ::= { hh3cEntityExtObjects 1 }

    hh3cEntityExtStateTable OBJECT-TYPE
        SYNTAX SEQUENCE OF Hh3cEntityExtStateEntry
        MAX-ACCESS not-accessible
        STATUS current
        DESCRIPTION
            "This table contains one row per physical entity, There is
            always at least one row for an 'overall' physical entity.
            The information in each row may be not include all the object
            in this table, because of the entity need not some of the
            information here."
        ::= { hh3cEntityExtState 1 }

    hh3cEntityExtStateEntry OBJECT-TYPE
        SYNTAX Hh3cEntityExtStateEntry
        MAX-ACCESS not-accessible
        STATUS current
        DESCRIPTION
            "The information about a particular physical entity."
        INDEX { hh3cEntityExtPhysicalIndex }
        ::= { hh3cEntityExtStateTable 1 }

    Hh3cEntityExtStateEntry ::= SEQUENCE {
        hh3cEntityExtPhysicalIndex
            INTEGER,
        hh3cEntityExtAdminStatus
            Hh3cAdminState,
        hh3cEntityExtOperStatus
            Hh3cOperState,
        hh3cEntityExtStandbyStatus
            Hh3cStandbyStatus,
        hh3cEntityExtAlarmLight
            Hh3cAlarmStatus,
        hh3cEntityExtCpuUsage
            INTEGER,
        hh3cEntityExtCpuUsageThreshold
            INTEGER,
        hh3cEntityExtMemUsage
            INTEGER,
        hh3cEntityExtMemUsageThreshold
            INTEGER,
        hh3cEntityExtMemSize
            INTEGER,
        hh3cEntityExtUpTime
            INTEGER,
        hh3cEntityExtTemperature
            INTEGER,
        hh3cEntityExtTemperatureThreshold
            INTEGER,
        hh3cEntityExtVoltage
            INTEGER,
        hh3cEntityExtVoltageLowThreshold
            INTEGER,
        hh3cEntityExtVoltageHighThreshold
            INTEGER,
        hh3cEntityExtCriticalTemperatureThreshold
            INTEGER,
        hh3cEntityExtMacAddress
            MacAddress,
        hh3cEntityExtErrorStatus
            INTEGER,
        hh3cEntityExtCpuMaxUsage
            Integer32
     }

    hh3cEntityExtPhysicalIndex OBJECT-TYPE
        SYNTAX INTEGER
        MAX-ACCESS accessible-for-notify
        STATUS current
        DESCRIPTION
            "The index of hh3cEntityExtStateTable.
            This index is identical to entPhysicalIndex in ENTITY-MIB"
        ::= { hh3cEntityExtStateEntry 1 }

    hh3cEntityExtAdminStatus OBJECT-TYPE
        SYNTAX Hh3cAdminState
        MAX-ACCESS read-write
        STATUS current
        DESCRIPTION
            "The administrative state for this object."
        ::= { hh3cEntityExtStateEntry 2 }

    hh3cEntityExtOperStatus OBJECT-TYPE
        SYNTAX Hh3cOperState
        MAX-ACCESS read-only
        STATUS current
        DESCRIPTION
            "The operate state for this object."
        ::= { hh3cEntityExtStateEntry 3 }

    hh3cEntityExtStandbyStatus OBJECT-TYPE
        SYNTAX Hh3cStandbyStatus
        MAX-ACCESS read-only
        STATUS current
        DESCRIPTION
            "This object is used for monitoring standby status.
            Not all entities support this object."
        ::= { hh3cEntityExtStateEntry 4 }

    hh3cEntityExtAlarmLight OBJECT-TYPE
        SYNTAX Hh3cAlarmStatus
        MAX-ACCESS read-only
        STATUS current
        DESCRIPTION
            "The alarm status for this entity. It does not include
            the severity of alarms raised on child components. In
            this condition, there will be a alarm light on the entity,
            the object should have the same status with it."
        ::= { hh3cEntityExtStateEntry 5 }

    hh3cEntityExtCpuUsage OBJECT-TYPE
        SYNTAX INTEGER (0..100)
        MAX-ACCESS read-only
        STATUS current
        DESCRIPTION
            "The CPU usage for this entity. Generally, the CPU usage
            will calculate the overall CPU usage on the entity, and it
            is not sensible with the number of CPU on the entity."
        ::= { hh3cEntityExtStateEntry 6 }

    hh3cEntityExtCpuUsageThreshold OBJECT-TYPE
        SYNTAX INTEGER (0..100)
        MAX-ACCESS read-write
        STATUS current
        DESCRIPTION
            "The threshold for the CPU usage. When the CPU usage exceeds
            the threshold, a notification will be sent."
        ::= { hh3cEntityExtStateEntry 7 }

    hh3cEntityExtMemUsage OBJECT-TYPE
        SYNTAX INTEGER (0..100)
        MAX-ACCESS read-only
        STATUS current
        DESCRIPTION
            "The memory usage for the entity. This object indicates what
            percent of memory are used."
        ::= { hh3cEntityExtStateEntry 8 }

    hh3cEntityExtMemUsageThreshold OBJECT-TYPE
        SYNTAX INTEGER (0..100)
        MAX-ACCESS read-write
        STATUS current
        DESCRIPTION
            "The threshold for the Memory usage, When the memory usage
            exceeds the threshold, a notification will be sent."
        ::= { hh3cEntityExtStateEntry 9 }

    hh3cEntityExtMemSize OBJECT-TYPE
        SYNTAX INTEGER
        UNITS "bytes"
        MAX-ACCESS read-only
        STATUS current
        DESCRIPTION
            "The size of memory for the entity."
        ::= { hh3cEntityExtStateEntry 10 }

    hh3cEntityExtUpTime OBJECT-TYPE
        SYNTAX INTEGER
        UNITS "seconds"
        MAX-ACCESS read-only
        STATUS current
        DESCRIPTION
            "The uptime for the entity. The meaning of uptime is
            when the entity is up, and the value of the object
            will add 1 seconds while the entity is running."
        ::= { hh3cEntityExtStateEntry 11 }

    hh3cEntityExtTemperature OBJECT-TYPE
        SYNTAX INTEGER
        MAX-ACCESS read-only
        STATUS current
        DESCRIPTION
            "The temperature for the entity."
        ::= { hh3cEntityExtStateEntry 12 }

    hh3cEntityExtTemperatureThreshold OBJECT-TYPE
        SYNTAX INTEGER
        MAX-ACCESS read-write
        STATUS current
        DESCRIPTION
            "The threshold for the temperature. When the temperature
            exceeds the threshold, a notification will be sent."
        ::= { hh3cEntityExtStateEntry 13 }

    hh3cEntityExtVoltage OBJECT-TYPE
        SYNTAX INTEGER
        MAX-ACCESS read-only
        STATUS current
        DESCRIPTION
            "The voltage for the entity."
        ::= { hh3cEntityExtStateEntry 14 }

    hh3cEntityExtVoltageLowThreshold OBJECT-TYPE
        SYNTAX INTEGER
        MAX-ACCESS read-write
        STATUS current
        DESCRIPTION
            "The low-threshold for the voltage.
            When voltage is lower than low-threshold, a notification will be
            sent."
        ::= { hh3cEntityExtStateEntry 15 }

    hh3cEntityExtVoltageHighThreshold OBJECT-TYPE
        SYNTAX INTEGER
        MAX-ACCESS read-write
        STATUS current
        DESCRIPTION
            "The high-threshold for the voltage.
            When voltage greater than high-threshold, a notification will be
            sent."
        ::= { hh3cEntityExtStateEntry 16 }

    hh3cEntityExtCriticalTemperatureThreshold OBJECT-TYPE
        SYNTAX INTEGER
        MAX-ACCESS read-write
        STATUS current
        DESCRIPTION
            " The threshold for the critical Temperature. When temperature
            exceeds the critical temperature, a notification will be sent."
        ::= { hh3cEntityExtStateEntry 17 }

    hh3cEntityExtMacAddress OBJECT-TYPE
        SYNTAX MacAddress
        MAX-ACCESS read-only
        STATUS current
        DESCRIPTION
            "MAC Address of the entity."
        ::= { hh3cEntityExtStateEntry 18 }

    hh3cEntityExtErrorStatus OBJECT-TYPE
        SYNTAX INTEGER
            {
            notSupported(1),
            normal(2),
            postFailure(3),
            entityAbsent(4),
            poeError(11),
            stackError(21),
            stackPortBlocked(22),
            stackPortFailed(23),
            sfpRecvError(31),
            sfpSendError(32),
            sfpBothError(33),
            fanError (41),
            psuError(51),
            rpsError(61),
            moduleFaulty(71),
            sensorError(81)
            }
        MAX-ACCESS read-only
        STATUS current
        DESCRIPTION
            "Indicate the error state of this entity object. Now it only
            supports Port, general power supply, RPS power supply and
            board/Subcard. It may have one of these values.
            The following four values  can be used for all kinds of entities.

            notSupported(1) means this entity can not support this function.
            normal(2) means the statement of this entity is normal. for ports,
            it doesn't differentiate 10M/s, 100M/s, 1000M/s, duplex and
            half-duplex. For fan, power supply and board-Subcard, it means
            their states are normal.
            postFailure(3)  means the entity fails to POST.
            entityAbsent(4) means the entity is absent now.


            The following values is depended on the entity .

            For Port entities, it may have the following  values. If its POST
            is failure,
            then the value of the instance will be postFailure(3), otherwise
            the value will be normal(2).

            If enable power supply over Ethernet on this port is failure,
            the value of this instance will be poeError(11), otherwise it will
            be normal(2).

            For stack port, if it connects to another stack port normally, and
            these two units merge into one stack, then the value of this
            instance will be normal(2).
            If something wrong occurs and the unit can not merge into stack,
            the value of this instance will be stackPortFailed(23).  If the
            stack port forms resilient daisy chain with another stack port
            on the other unit, the value of this instance will be
            stackPortBlocked(22).


            For SFP ports, if it fail to receive, the value of this instance
            will be sfpRecvError(31), if it fail to send, the value is
            sfpSendError(32), if it fail to send and receive, the value is
            sfpBothError(33), otherwise it will be normal(2).

            fanError(41) means that the fan stops working.

            psuError(51) means that the Power Supply Unit is in the state of
            fault.

            rpsError(61) means the RPS is in the state of fault.

            moduleFaulty(71) means the Module is in the state of fault.

            sensorError(81) means the sensor is in the state of fault.

            NMS must be compatible with the states which may be added
            in the future."
        ::= { hh3cEntityExtStateEntry 19 }

    hh3cEntityExtCpuMaxUsage OBJECT-TYPE
        SYNTAX Integer32(0..100)
        MAX-ACCESS read-only
        STATUS current
        DESCRIPTION
            "The maximal CPU usage for the entity in the period of time."
        ::= { hh3cEntityExtStateEntry 20 }

    hh3cEntityExtManu OBJECT IDENTIFIER ::= { hh3cEntityExtObjects 2 }

    hh3cEntityExtManuTable OBJECT-TYPE
        SYNTAX SEQUENCE OF Hh3cEntityExtManuEntry
        MAX-ACCESS not-accessible
        STATUS current
        DESCRIPTION
            "The table about device manufacture information."
        ::= { hh3cEntityExtManu 1 }

    hh3cEntityExtManuEntry OBJECT-TYPE
        SYNTAX Hh3cEntityExtManuEntry
        MAX-ACCESS not-accessible
        STATUS current
        DESCRIPTION
            "The device manufacture information about a particular physical
            entity."
        INDEX { hh3cEntityExtManuPhysicalIndex }
        ::= { hh3cEntityExtManuTable 1 }

    Hh3cEntityExtManuEntry ::= SEQUENCE {
        hh3cEntityExtManuPhysicalIndex
            Integer32,
        hh3cEntityExtManuSerialNum
            SnmpAdminString,
        hh3cEntityExtManuBuildInfo
            SnmpAdminString,
        hh3cEntityExtManuBOM
            SnmpAdminString,
        hh3cEntityExtMacAddressCount
            Unsigned32
     }

    hh3cEntityExtManuPhysicalIndex OBJECT-TYPE
        SYNTAX Integer32 (1..2147483647)
        MAX-ACCESS accessible-for-notify
        STATUS current
        DESCRIPTION
            "The index of hh3cEntityExtManuTable.
            This index is identical to entPhysicalIndex in ENTITY-MIB."
        ::= { hh3cEntityExtManuEntry 1 }

    hh3cEntityExtManuSerialNum OBJECT-TYPE
        SYNTAX SnmpAdminString
        MAX-ACCESS read-only
        STATUS current
        DESCRIPTION
            "Manufacture serial number.
            The manufacture serial number of the entity such as chassis,
            module, and so on.  It is got from the device when manufacturing.
            For low level box-device, the manufacture serial number is the
            device-number of System Control Board(SCB for short), it is written
            into the SCB directly; for middle level or high level frame-device,
            the manufacture serial number is the device-numbers of SCB and
            Service Board, because the SCB, Service Board and chassis are
            separate to sale and the device-number of chassis can not be
            written into board."
        ::= { hh3cEntityExtManuEntry 2 }

    hh3cEntityExtManuBuildInfo OBJECT-TYPE
        SYNTAX SnmpAdminString
        MAX-ACCESS read-only
        STATUS current
        DESCRIPTION
            "Device version information.
            The device version information of the entity such as chassis,
            module, and so on.  It consists of software version information
            and hardware version information."
        ::= { hh3cEntityExtManuEntry 3 }

    hh3cEntityExtManuBOM OBJECT-TYPE
        SYNTAX SnmpAdminString
        MAX-ACCESS read-only
        STATUS current
        DESCRIPTION
            "Device BOM code.
            The device BOM code of the entity such as chassis, module, and so
            on.  It is the component code of ERP system, which can be
            disassembled from device-number."
        ::= { hh3cEntityExtManuEntry 4 }

    hh3cEntityExtMacAddressCount OBJECT-TYPE
        SYNTAX Unsigned32
        MAX-ACCESS read-only
        STATUS current
        DESCRIPTION
            "MAC address count.
            The count of MAC addresses of the entity, such as chassis, module,
            or port, and so on."
        ::= { hh3cEntityExtManuEntry 5 }

    hh3cEntityExtPower OBJECT IDENTIFIER ::= { hh3cEntityExtObjects 3 }

    hh3cEntityExtPowerTable OBJECT-TYPE
        SYNTAX SEQUENCE OF Hh3cEntityExtPowerEntry
        MAX-ACCESS not-accessible
        STATUS current
        DESCRIPTION
            "This table describes the power information of all the physical
            entity on the device, such as the fans, the subcards, the boards,
            etc."
        ::= { hh3cEntityExtPower 1 }

    hh3cEntityExtPowerEntry OBJECT-TYPE
        SYNTAX Hh3cEntityExtPowerEntry
        MAX-ACCESS not-accessible
        STATUS current
        DESCRIPTION
            "The entity power information about a particular physical entity."
        INDEX { hh3cEntityExtPowerPhysicalIndex }
        ::= { hh3cEntityExtPowerTable 1 }

    Hh3cEntityExtPowerEntry ::= SEQUENCE {
        hh3cEntityExtPowerPhysicalIndex
            Integer32,
        hh3cEntityExtNominalPower
            Gauge32,
        hh3cEntityExtCurrentPower
            Gauge32,
        hh3cEntityExtAveragePower
            Integer32,
        hh3cEntityExtPeakPower
            Integer32
     }

    hh3cEntityExtPowerPhysicalIndex OBJECT-TYPE
        SYNTAX Integer32 (1..2147483647)
        MAX-ACCESS accessible-for-notify
        STATUS current
        DESCRIPTION
            "The index of hh3cEntityExtPowerTable.
            This index is identical to entPhysicalIndex in ENTITY-MIB."
        ::= { hh3cEntityExtPowerEntry 1 }

    hh3cEntityExtNominalPower OBJECT-TYPE
        SYNTAX Gauge32
        MAX-ACCESS read-only
        STATUS current
        DESCRIPTION
            "The nominal power of the entity expressed in milliWatts."
        ::= { hh3cEntityExtPowerEntry 2 }

    hh3cEntityExtCurrentPower OBJECT-TYPE
        SYNTAX Gauge32
        MAX-ACCESS read-only
        STATUS current
        DESCRIPTION
            "The measured usage power of the entity expressed in milliWatts."
        ::= { hh3cEntityExtPowerEntry 3 }

    hh3cEntityExtAveragePower OBJECT-TYPE
        SYNTAX Integer32
        MAX-ACCESS read-write
        STATUS current
        DESCRIPTION
            "The average power consumed by the entity expressed in milliWatts.
            Writing a value of zero to this object resets its value to zero.
            Writing any other value to this object has no effect on its value
            and an error is returned."
        ::= { hh3cEntityExtPowerEntry 4 }

    hh3cEntityExtPeakPower OBJECT-TYPE
        SYNTAX Integer32
        MAX-ACCESS read-write
        STATUS current
        DESCRIPTION
            "The peak power consumed by the entity expressed in milliWatts.
            Writing a value of zero to this object resets its value to zero.
            Writing any other value to this object has no effect on its value
            and an error is returned."
        ::= { hh3cEntityExtPowerEntry 5 }

    hh3cEntityExtTraps OBJECT IDENTIFIER ::= { hh3cEntityExtend 2 }

    hh3cEntityExtTrapsPrefix OBJECT IDENTIFIER ::= { hh3cEntityExtTraps 0 }

    hh3cEntityExtTemperatureThresholdNotification NOTIFICATION-TYPE
        OBJECTS {
            hh3cEntityExtPhysicalIndex,
            hh3cEntityExtTemperature,
            hh3cEntityExtTemperatureThreshold,
            hh3cEntityExtAdminStatus,
            hh3cEntityExtAlarmLight
            }
        STATUS current
        DESCRIPTION
            "The hh3cEntityExtTemperatureThresholdNotification
            indicates the temperature exceeded the threshold.
            In this condition, user should check the status and the
            environment of the entity, sometimes it happens because
            of the failure of air-condition."
        ::= { hh3cEntityExtTrapsPrefix 1 }

    hh3cEntityExtVoltageLowThresholdNotification NOTIFICATION-TYPE
        OBJECTS {
            hh3cEntityExtPhysicalIndex,
            hh3cEntityExtVoltage,
            hh3cEntityExtVoltageLowThreshold,
            hh3cEntityExtAdminStatus,
            hh3cEntityExtAlarmLight
            }
        STATUS current
        DESCRIPTION
            "The hh3cEntityExtVoltageLowThresholdNotification indicates
            the voltage is lower than the threshold.

            If the voltage is lower too much than the entity needs,
            the entity will halt."
        ::= { hh3cEntityExtTrapsPrefix 2 }

    hh3cEntityExtVoltageHighThresholdNotification NOTIFICATION-TYPE
        OBJECTS {
            hh3cEntityExtPhysicalIndex,
            hh3cEntityExtVoltage,
            hh3cEntityExtVoltageHighThreshold,
            hh3cEntityExtAdminStatus,
            hh3cEntityExtAlarmLight
            }
        STATUS current
        DESCRIPTION
            "The hh3cEntityExtVoltageHighThresholdNotification indicates
            the voltage is higher than the threshold.

            If the voltage is higher too much than the entity needs,
            The entity may be damaged by the high voltage."
        ::= { hh3cEntityExtTrapsPrefix 3 }

    hh3cEntityExtCpuUsageThresholdNotfication NOTIFICATION-TYPE
        OBJECTS {
            hh3cEntityExtPhysicalIndex,
            hh3cEntityExtCpuUsage,
            hh3cEntityExtCpuUsageThreshold,
            hh3cEntityExtAdminStatus,
            hh3cEntityExtAlarmLight
            }
        STATUS current
        DESCRIPTION
            "The hh3cEntityExtCpuUsageThresholdNotfication indicates
            the entity is overloaded."
        ::= { hh3cEntityExtTrapsPrefix 4 }

    hh3cEntityExtMemUsageThresholdNotification NOTIFICATION-TYPE
        OBJECTS {
            hh3cEntityExtPhysicalIndex,
            hh3cEntityExtMemUsage,
            hh3cEntityExtMemUsageThreshold,
            hh3cEntityExtMemSize,
            hh3cEntityExtAdminStatus,
            hh3cEntityExtAlarmLight
            }
        STATUS current
        DESCRIPTION
            "The hh3cEntityExtMemUsageThresholdNotification indicates
            the entity is overloaded."
        ::= { hh3cEntityExtTrapsPrefix 5 }

    hh3cEntityExtOperEnabled NOTIFICATION-TYPE
        OBJECTS {
            hh3cEntityExtPhysicalIndex,
            hh3cEntityExtAdminStatus,
            hh3cEntityExtAlarmLight
            }
        STATUS current
        DESCRIPTION
            "The trap indicates the entity is operable at present."
        ::= { hh3cEntityExtTrapsPrefix 6 }

    hh3cEntityExtOperDisabled NOTIFICATION-TYPE
        OBJECTS {
            hh3cEntityExtPhysicalIndex,
            hh3cEntityExtAdminStatus,
            hh3cEntityExtAlarmLight
            }
        STATUS current
        DESCRIPTION
            "The trap indicates the entity is not operable at present."
        ::= { hh3cEntityExtTrapsPrefix 7 }

    hh3cEntityExtCriticalTemperatureThresholdNotification NOTIFICATION-TYPE
        OBJECTS {
            hh3cEntityExtPhysicalIndex,
            hh3cEntityExtTemperature,
            hh3cEntityExtCriticalTemperatureThreshold,
            hh3cEntityExtAdminStatus,
            hh3cEntityExtAlarmLight
            }
        STATUS current
        DESCRIPTION
            "The hh3cEntityExtCriticalTemperatureThresholdNotification
            indicates the temperature exceeds the critical temperature.
            In this condition, user should check the status and the
            environment of the entity, sometimes it happens because
            of the failure of air-condition."
        ::= { hh3cEntityExtTrapsPrefix 8 }

    hh3cEntityExtSFPAlarmOn NOTIFICATION-TYPE
        OBJECTS {
            hh3cEntityExtPhysicalIndex,
            hh3cEntityExtErrorStatus,
            hh3cEntityExtAdminStatus,
            hh3cEntityExtAlarmLight
            }
        STATUS current
        DESCRIPTION
            "The trap is generated when the SFP module fails
            or runs abnormally for some particular reason."
        ::= { hh3cEntityExtTrapsPrefix 9 }

    hh3cEntityExtSFPAlarmOff NOTIFICATION-TYPE
        OBJECTS {
            hh3cEntityExtPhysicalIndex,
            hh3cEntityExtErrorStatus,
            hh3cEntityExtAdminStatus,
            hh3cEntityExtAlarmLight
            }
        STATUS current
        DESCRIPTION
            "The trap is generated when the SFP module restores to
            normal status."
        ::= { hh3cEntityExtTrapsPrefix 10 }

    hh3cEntityExtSFPPhony NOTIFICATION-TYPE
        OBJECTS {
            hh3cEntityExtPhysicalIndex,
            entPhysicalName,
            hh3cEntityExtAdminStatus,
            hh3cEntityExtAlarmLight
            }
        STATUS current
        DESCRIPTION
            "This module is NOT sold by H3C. H3C therefore shall NOT guarantee
            the normal function of the device or assume the maintenance
            responsibility thereof. The trap is generated periodically after
            a phony module has been found."
        ::= { hh3cEntityExtTrapsPrefix 11 }

--  Conformance and Compliance
    hh3cEntityExtConformance OBJECT IDENTIFIER ::= { hh3cEntityExtend 3 }

    hh3cEntityExtCompliances OBJECT IDENTIFIER ::= { hh3cEntityExtConformance 1 }

--  this module
    hh3cEntityExtCompliance MODULE-COMPLIANCE
        STATUS current
        DESCRIPTION
            "The compliance statement for systems supporting this MIB."
        MODULE -- this module
            MANDATORY-GROUPS { hh3cEntityExtGroup }
            OBJECT hh3cEntityExtAdminStatus
                MIN-ACCESS read-only
                DESCRIPTION
                    "Write access is not required."
            OBJECT hh3cEntityExtCpuUsageThreshold
                MIN-ACCESS read-only
                DESCRIPTION
                    "Write access is not required."
            OBJECT hh3cEntityExtMemUsageThreshold
                MIN-ACCESS read-only
                DESCRIPTION
                    "Write access is not required."
            OBJECT hh3cEntityExtTemperatureThreshold
                MIN-ACCESS read-only
                DESCRIPTION
                    "Write access is not required."
            OBJECT hh3cEntityExtVoltageLowThreshold
                MIN-ACCESS read-only
                DESCRIPTION
                    "Write access is not required."
            OBJECT hh3cEntityExtVoltageHighThreshold
                MIN-ACCESS read-only
                DESCRIPTION
                    "Write access is not required."
        ::= { hh3cEntityExtCompliances 1 }

    hh3cEntityExtGroups OBJECT IDENTIFIER ::= { hh3cEntityExtConformance 2 }

    hh3cEntityExtGroup OBJECT-GROUP
        OBJECTS {
            hh3cEntityExtPhysicalIndex,
            hh3cEntityExtAdminStatus,
            hh3cEntityExtOperStatus,
            hh3cEntityExtStandbyStatus,
            hh3cEntityExtAlarmLight,
            hh3cEntityExtCpuUsage,
            hh3cEntityExtCpuUsageThreshold,
            hh3cEntityExtMemUsage,
            hh3cEntityExtMemUsageThreshold,
            hh3cEntityExtMemSize,
            hh3cEntityExtUpTime,
            hh3cEntityExtTemperature,
            hh3cEntityExtTemperatureThreshold,
            hh3cEntityExtVoltage,
            hh3cEntityExtVoltageLowThreshold,
            hh3cEntityExtVoltageHighThreshold,
            hh3cEntityExtCriticalTemperatureThreshold,
            hh3cEntityExtMacAddress,
            hh3cEntityExtErrorStatus,
            hh3cEntityExtCpuMaxUsage
            }
        STATUS current
        DESCRIPTION
            "Standard HH3C Entity Extend group."
        ::= { hh3cEntityExtGroups 1 }

    hh3cEntityExtNotificationGroup NOTIFICATION-GROUP
        NOTIFICATIONS { hh3cEntityExtTemperatureThresholdNotification,
                hh3cEntityExtVoltageLowThresholdNotification,
                hh3cEntityExtVoltageHighThresholdNotification,
                hh3cEntityExtCpuUsageThresholdNotfication,
                hh3cEntityExtMemUsageThresholdNotification,
                hh3cEntityExtOperEnabled,
                hh3cEntityExtOperDisabled,
                hh3cEntityExtCriticalTemperatureThresholdNotification,
                hh3cEntityExtSFPAlarmOn,
                hh3cEntityExtSFPAlarmOff,
                hh3cEntityExtSFPPhony
                 }
        STATUS current
        DESCRIPTION
            "Standard Entity Extend Notification group for H3C."
            ::= { hh3cEntityExtGroups 2 }

    hh3cEntityExtManuGroup OBJECT-GROUP
        OBJECTS {
            hh3cEntityExtManuPhysicalIndex,
            hh3cEntityExtManuSerialNum,
            hh3cEntityExtManuBuildInfo,
            hh3cEntityExtManuBOM,
            hh3cEntityExtMacAddressCount
            }
        STATUS current
        DESCRIPTION
            "Standard Device Manufacture Information group."
        ::= { hh3cEntityExtGroups 3 }

    hh3cEntityExtPowerGroup OBJECT-GROUP
        OBJECTS {
            hh3cEntityExtPowerPhysicalIndex,
            hh3cEntityExtNominalPower,
            hh3cEntityExtCurrentPower,
            hh3cEntityExtAveragePower,
            hh3cEntityExtPeakPower
            }
        STATUS current
        DESCRIPTION
            "Standard Entity Power Information group."
        ::= { hh3cEntityExtGroups 4 }

    END
