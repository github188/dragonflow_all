-- *****************************************************************
-- CISCO-SYSLOG-CAPABILITY.my:
-- Cisco CISCO-SYSLOG-MIB AGENT-CAPABILITIES
--   
-- Oct 2003, Jayakumar Kadirvelu
--   
-- Copyright (c) 2003-2004, 2006-2008 by Cisco Systems Inc.
-- All rights reserved.
-- *****************************************************************

CISCO-SYSLOG-CAPABILITY DEFINITIONS ::= BEGIN

IMPORTS
    MODULE-IDENTITY
        FROM SNMPv2-SMI
    AGENT-CAPABILITIES
        FROM SNMPv2-CONF
    ciscoAgentCapability
        FROM CISCO-SMI;


ciscoSyslogCapability MODULE-IDENTITY
    LAST-UPDATED    "200808110000Z"
    ORGANIZATION    "Cisco Systems, Inc."
    CONTACT-INFO
            "Cisco Systems
            Customer Service

            Postal: 170 West Tasman Drive
            San Jose, CA  95134
            USA

            Tel: +1 800 553-NETS

            E-mail: cs-lan-switch-snmp@cisco.com
            cs-snmp@cisco.com"
    DESCRIPTION
        "The capabilities description of CISCO-SYSLOG-MIB."
    REVISION        "200808110000Z"
    DESCRIPTION
        "Adding newlines at the end of the MIB file."
    REVISION        "200806080000Z"
    DESCRIPTION
        "Added Agent capability for ACE 4710 Application 
        Control Engine Appliance."

    REVISION        "200610260000Z"
    DESCRIPTION
        "Added capability for Cisco TelePresence System (CTS) and
        Cisco TelePresence Manager (CTM) platforms."
    REVISION        "200605250000Z"
    DESCRIPTION
        "Added Agent capability
        ciscoSyslogCapACSWV03R000 for
        Application Control Engine (ACE)."
    REVISION        "200402030000Z"
    DESCRIPTION
        "Initial version of this MIB module."
    ::= { ciscoAgentCapability 61 }



ciscoSyslogCapCatOSV08R0101 AGENT-CAPABILITIES
    PRODUCT-RELEASE "Cisco CatOS 8.1(1)."
    STATUS          current
    DESCRIPTION
        "CISCO-SYSLOG-MIB capabilities."

    SUPPORTS        CISCO-SYSLOG-MIB
    INCLUDES        { ciscoSyslogMIBGroup }
    ::= { ciscoSyslogCapability 1 }

ciscoSyslogCapACSWV03R000 AGENT-CAPABILITIES
    PRODUCT-RELEASE "ACSW (Application Control Software) 3.0
 
                   for Application Control Engine(ACE)

                    Service Module."
    STATUS          current
    DESCRIPTION
        "CISCO-SYSLOG-MIB capabilities."

    SUPPORTS        CISCO-SYSLOG-MIB
    INCLUDES        {
                        ciscoSyslogMIBGroup,
                        clogOriginIDGroup,
                        clogNotificationsGroup
                    }
    VARIATION       clogNotificationsEnabled
    ACCESS          read-only
    DESCRIPTION
        "write operation not suppported."

    VARIATION       clogMaxSeverity
    ACCESS          read-only
    DESCRIPTION
        "write operation not suppported."

    VARIATION       clogHistTableMaxLength
    ACCESS          read-only
    DESCRIPTION
        "write operation not suppported."

    VARIATION       clogOriginIDType
    ACCESS          read-only
    DESCRIPTION
        "write operation not suppported."

    VARIATION       clogOriginID
    ACCESS          read-only
    DESCRIPTION
        "write operation not suppported."

    VARIATION       clogMessageGenerated
    DESCRIPTION
        "The notification is sent with additional
        varbinds.  Additonal varbinds clogOriginIDType and
        clogOriginID are included in the notification PDU.
        These varbinds help in finding the source of the
        notification."

    ::= { ciscoSyslogCapability 2 }

ciscoSyslogCapCTSV100 AGENT-CAPABILITIES
    PRODUCT-RELEASE "Cisco TelePresence System (CTS) 1.0.0."
    STATUS          current
    DESCRIPTION
        "CISCO-SYSLOG-MIB capabilities."

    SUPPORTS        CISCO-SYSLOG-MIB
    INCLUDES        {
                        ciscoSyslogMIBGroup,
                        clogOriginIDGroup,
                        clogNotificationsGroup
                    }
    ::= { ciscoSyslogCapability 3 }

ciscoSyslogCapCTMV1000 AGENT-CAPABILITIES
    PRODUCT-RELEASE "Cisco TelePresence Manager (CTM) 1.0.0.0."
    STATUS          current
    DESCRIPTION
        "CISCO-SYSLOG-MIB capabilities."

    SUPPORTS        CISCO-SYSLOG-MIB
    INCLUDES        {
                        ciscoSyslogMIBGroup,
                        clogOriginIDGroup,
                        clogNotificationsGroup
                    }
    ::= { ciscoSyslogCapability 4 }

ciscoSyslogCapc4710aceVA1R70 AGENT-CAPABILITIES
    PRODUCT-RELEASE "ACSW (Application Control Software) A1(7)
                    for ACE 4710 Application Control Engine 
                    Appliance."
    STATUS          current
    DESCRIPTION
        "CISCO-SYSLOG-MIB capabilities."

    SUPPORTS        CISCO-SYSLOG-MIB
    INCLUDES        {
                        ciscoSyslogMIBGroup,
                        clogOriginIDGroup,
                        clogNotificationsGroup
                    }
    VARIATION       clogNotificationsEnabled
    ACCESS          read-only
    DESCRIPTION
        "write operation not suppported."

    VARIATION       clogMaxSeverity
    ACCESS          read-only
    DESCRIPTION
        "write operation not suppported."

    VARIATION       clogHistTableMaxLength
    ACCESS          read-only
    DESCRIPTION
        "write operation not suppported."

    VARIATION       clogOriginIDType
    ACCESS          read-only
    DESCRIPTION
        "write operation not suppported."

    VARIATION       clogOriginID
    ACCESS          read-only
    DESCRIPTION
        "write operation not suppported."

    VARIATION       clogMessageGenerated
    DESCRIPTION
        "The notification is sent with additional
        varbinds.  Additonal varbinds clogOriginIDType and
        clogOriginID are included in the notification PDU.
        These varbinds help in finding the source of the
        notification."

    ::= { ciscoSyslogCapability 5 }

END
