-- =================================================================
-- Copyright (C) 2002-2004 by  H3C TECHNOLOGIES. All rights reserved.
--
-- Description:
-- Reference:H3C enterprise mib
-- =================================================================
HH3C-USER-MIB DEFINITIONS ::= BEGIN
IMPORTS
    hh3cCommon
        FROM HH3C-OID-MIB
    OBJECT-GROUP, MODULE-COMPLIANCE
        FROM SNMPv2-CONF
    RowStatus, MacAddress, TEXTUAL-CONVENTION
        FROM SNMPv2-TC
    IpAddress, Integer32, Counter32, OBJECT-TYPE, MODULE-IDENTITY
        FROM SNMPv2-SMI;

hh3cUser MODULE-IDENTITY
    LAST-UPDATED "200304100000Z"            -- April 10, 2003 at 00:00 GMT
    ORGANIZATION
        "Hangzhou H3C Tech. Co., Ltd."
    CONTACT-INFO
        "Platform Team Hangzhou H3C Tech. Co., Ltd.
        Hai-Dian District Beijing P.R. China
        http://www.h3c.com
        Zip:100085
        "
    DESCRIPTION
        "
        This MIB contains objects to
        Manage configuration and Monitor running state
        for userlog feature.
        "
    ::= { hh3cCommon 12 }


--
--type definitions
--

--DisplayString
DisplayString     ::=
        OCTET STRING
-- This data type is used to model textual information taken
-- from the NVT ASCII character set.  By convention, objects
-- with this syntax are declared as having
--
        (SIZE (0..255))

--ServiceType
ServiceType ::=  TEXTUAL-CONVENTION
    STATUS      current
    DESCRIPTION
        "enable (1)
        disable (2)
        "
    SYNTAX      INTEGER
        {
            enable(1),
            disable(2)
        }
--
--end of type definitions
--

-- hh3cUserObjects===============================================================
hh3cUserObjects OBJECT IDENTIFIER ::= { hh3cUser 1 }


-- hh3cUserInfoTable=============================================================
hh3cUserInfoTable OBJECT-TYPE
    SYNTAX      SEQUENCE OF Hh3cUserInfoEntry
    MAX-ACCESS  not-accessible
    STATUS      current
    DESCRIPTION
        "
        Local User Info Table
        "
    ::= { hh3cUserObjects 1 }

hh3cUserInfoEntry OBJECT-TYPE
    SYNTAX      Hh3cUserInfoEntry
    MAX-ACCESS  not-accessible
    STATUS      current
    DESCRIPTION
        "
        The entry of hh3cUserInfoTable
        "
    INDEX
        {
            hh3cUserIndex
        }
    ::= { hh3cUserInfoTable 1 }

Hh3cUserInfoEntry ::= SEQUENCE
    {
        hh3cUserName             DisplayString,
        hh3cUserPassword         DisplayString,
        hh3cAuthMode             Integer32,
        hh3cUserLevel            Integer32,
        hh3cUserState            INTEGER,
        hh3cUserInfoRowStatus    RowStatus,
        hh3cUserIndex            Integer32
    }


hh3cUserName OBJECT-TYPE
    SYNTAX      DisplayString
    MAX-ACCESS  read-create
    STATUS      current
    DESCRIPTION
        "
        The name of local user, it must be unique.
        "
    ::= { hh3cUserInfoEntry 1 }

hh3cUserPassword OBJECT-TYPE
    SYNTAX      DisplayString
    MAX-ACCESS  read-create
    STATUS      current
    DESCRIPTION
        "
        The password of local user, default is null.
        "
    ::= { hh3cUserInfoEntry 2 }

hh3cAuthMode OBJECT-TYPE
    SYNTAX      Integer32
    MAX-ACCESS  read-create
    STATUS      current
    DESCRIPTION
        "
        The encrypting type of password:
        0 : password simple, means password is clean text.
        7 : password cipher, means password is encrypted text.
        default is 0.
        "
    ::= { hh3cUserInfoEntry 3 }

hh3cUserLevel OBJECT-TYPE
    SYNTAX      Integer32
    MAX-ACCESS  read-create
    STATUS      current
    DESCRIPTION
        "
        The privilege of local user
        the value range is from 0 to 3, and 0 is minimum, 3 is maximum.
        default is 0.
        "
    ::= { hh3cUserInfoEntry 4 }

hh3cUserState OBJECT-TYPE
    SYNTAX      INTEGER
        {
            active(0),
            block(1)
        }
    MAX-ACCESS  read-create
    STATUS      current
    DESCRIPTION
        "
        The state of local user
        0: active, means local user can execute any operations that he has
           privilege to do.
        1: block, means local user can not execute any operations.
        default is active.
        "
    ::= { hh3cUserInfoEntry 5 }

hh3cUserInfoRowStatus OBJECT-TYPE
    SYNTAX      RowStatus
    MAX-ACCESS  read-create
    STATUS      current
    DESCRIPTION
        "
        The status of this conceptual row. Now only support CreateAndGo and
        Destroy and Active.
        "
    ::= { hh3cUserInfoEntry 6 }


hh3cUserIndex OBJECT-TYPE
    SYNTAX      Integer32
    MAX-ACCESS  not-accessible
    STATUS      current
    DESCRIPTION
        "
        The index of local user
        "
    ::= { hh3cUserInfoEntry 7 }


-- hh3cUserAttributeTable========================================================
hh3cUserAttributeTable OBJECT-TYPE
    SYNTAX      SEQUENCE OF Hh3cUserAttributeEntry
    MAX-ACCESS  not-accessible
    STATUS      current
    DESCRIPTION
        "
        Local User Attribute Table.
        if there are data in hh3cUserInfoTable, this table should have the
        relevant data.
        this table only support query and modify, but not support create and
        delete operations.
        "
    ::= { hh3cUserObjects 2 }

hh3cUserAttributeEntry OBJECT-TYPE
    SYNTAX      Hh3cUserAttributeEntry
    MAX-ACCESS  not-accessible
    STATUS      current
    DESCRIPTION
        "The entry of hh3cUserAttributeTable "
    INDEX
        {
            hh3cUserIndex
        }
    ::= { hh3cUserAttributeTable 1 }

Hh3cUserAttributeEntry ::= SEQUENCE
    {
        hh3cAccessLimit         Integer32,
        hh3cIdleCut             Integer32,
        hh3cIPAddress           IpAddress,
        hh3cNasIPAddress        IpAddress,
        hh3cSlotNum             Integer32,
        hh3cSubSlotNum          Integer32,
        hh3cPortNum             Integer32,
        hh3cMacAddress          MacAddress,
        hh3cVlan                Integer32,
        hh3cFtpService          ServiceType,
        hh3cFtpDirectory        OCTET STRING,
        hh3cLanAccessService    ServiceType,
        hh3cSshService          ServiceType,
        hh3cTelnetService       ServiceType,
        hh3cTerminalService     ServiceType
    }


hh3cAccessLimit OBJECT-TYPE
    SYNTAX      Integer32
    MAX-ACCESS  read-write
    STATUS      current
    DESCRIPTION
        "
        The maximum user number of current user who can access devices.
        default is 0, means no limit.
        "
    ::= { hh3cUserAttributeEntry 1 }

hh3cIdleCut OBJECT-TYPE
    SYNTAX      Integer32
    MAX-ACCESS  read-write
    STATUS      current
    DESCRIPTION
        "
        Valid idle time out(second): 60..7200,
        default is 0, means disable idle time out.
        "
    ::= { hh3cUserAttributeEntry 2 }

hh3cIPAddress OBJECT-TYPE
    SYNTAX      IpAddress
    MAX-ACCESS  read-write
    STATUS      current
    DESCRIPTION
        "
        Set local user's ip address.
        default is 0.0.0.0
        "
    ::= { hh3cUserAttributeEntry 3 }

hh3cNasIPAddress OBJECT-TYPE
    SYNTAX      IpAddress
    MAX-ACCESS  read-write
    STATUS      current
    DESCRIPTION
        "
        Set local user's ip address of network access server.
        default is 127.0.0.1, means local machine.
        "
    ::= { hh3cUserAttributeEntry 4 }

hh3cSlotNum OBJECT-TYPE
    SYNTAX      Integer32
    MAX-ACCESS  read-write
    STATUS      current
    DESCRIPTION
        "
        Set local user's slot.
        default is 0.
        "
    ::= { hh3cUserAttributeEntry 5 }

hh3cSubSlotNum OBJECT-TYPE
    SYNTAX      Integer32
    MAX-ACCESS  read-write
    STATUS      current
    DESCRIPTION
        "
        Set local user's sub-slot.
        default is 0.
        "
    ::= { hh3cUserAttributeEntry 6 }

hh3cPortNum OBJECT-TYPE
    SYNTAX      Integer32
    MAX-ACCESS  read-write
    STATUS      current
    DESCRIPTION
        "
        Set local user's port number.
        0 is an insignificant value for initial status.
        "
    ::= { hh3cUserAttributeEntry 7 }

hh3cMacAddress OBJECT-TYPE
    SYNTAX      MacAddress
    MAX-ACCESS  read-write
    STATUS      current
    DESCRIPTION
        "
        Set local user's mac address.
        default is 0-0-0, means the local user do not bind any mac address.
        "
    ::= { hh3cUserAttributeEntry 8 }

hh3cVlan OBJECT-TYPE
    SYNTAX      Integer32(0..4094)
    MAX-ACCESS  read-write
    STATUS      current
    DESCRIPTION
        "
        Set local user's vlan id.
        the value range is from 0 to 4094.
        default is 0, means the local user is not in any vlan.
        "
    ::= { hh3cUserAttributeEntry 9 }

hh3cFtpService OBJECT-TYPE
    SYNTAX      ServiceType
    MAX-ACCESS  read-write
    STATUS      current
    DESCRIPTION
        "
        FTP service:
        enable
        Setting this object to the value enable has the
        effect of enabling the FTP service for the corresponding entry in the
        hh3cUserAttributeTable.

        disable
        Setting this object to the value disable has the
        effect of disabling the FTP service for the corresponding entry in the
        hh3cUserAttributeTable.

        The default value is disable.
        "
    ::= { hh3cUserAttributeEntry 10 }

hh3cFtpDirectory OBJECT-TYPE
    SYNTAX      OCTET STRING
    MAX-ACCESS  read-write
    STATUS      current
    DESCRIPTION
        "
        Directory of FTP user.
        default is null, means if local user has the privilege of ftp service.
        "
    ::= { hh3cUserAttributeEntry 11 }

hh3cLanAccessService OBJECT-TYPE
    SYNTAX      ServiceType
    MAX-ACCESS  read-write
    STATUS      current
    DESCRIPTION
        "
        Lan Access service:
        enable
        Setting this object to the value enable has the
        effect of enabling the lan access service for the corresponding entry
        in the hh3cUserAttributeTable.

        disable
        Setting this object to the value disable has the
        effect of disabling the lan access service for the corresponding entry
        in the hh3cUserAttributeTable.

        The default value is disable.
        "
    ::= { hh3cUserAttributeEntry 12 }

hh3cSshService OBJECT-TYPE
    SYNTAX      ServiceType
    MAX-ACCESS  read-write
    STATUS      current
    DESCRIPTION
        "
        SSH service:
        enable
        Setting this object to the value enable has the
        effect of enabling the SSH service for the corresponding entry in the
        hh3cUserAttributeTable.

        disable
        Setting this object to the value disable has the
        effect of disabling the SSH service for the corresponding entry in the
        hh3cUserAttributeTable.

        The default value is disable.
        "
    ::= { hh3cUserAttributeEntry 13 }

hh3cTelnetService OBJECT-TYPE
    SYNTAX      ServiceType
    MAX-ACCESS  read-write
    STATUS      current
    DESCRIPTION
        "
        Telnet service:
        enable
        Setting this object to the value enable has the
        effect of enabling the TELNET service for the corresponding entry in the
        hh3cUserAttributeTable.

        disable
        Setting this object to the value disable has the
        effect of disabling the TELNET service for the corresponding entry in the
        hh3cUserAttributeTable.

        The default value is disable.
        "
    ::= { hh3cUserAttributeEntry 14 }

hh3cTerminalService OBJECT-TYPE
    SYNTAX      ServiceType
    MAX-ACCESS  read-write
    STATUS      current
    DESCRIPTION
        "
        Terminal service:
        enable
        Setting this object to the value enable has the
        effect of enabling the terminal service for the corresponding entry
        in the hh3cUserAttributeTable.

        disable
        Setting this object to the value disable has the
        effect of disabling the terminal service for the corresponding entry
        in the hh3cUserAttributeTable.

        The default value is disable.
        "
    ::= { hh3cUserAttributeEntry 15 }

-- hh3cUserMaxNum================================================================
hh3cUserMaxNum OBJECT-TYPE
    SYNTAX      Integer32
    MAX-ACCESS  read-only
    STATUS      current
    DESCRIPTION
        "
        This object contains the maximum number of local users.
        "
    ::= { hh3cUserObjects 3 }

-- hh3cUserCurrNum===============================================================
hh3cUserCurrNum OBJECT-TYPE
    SYNTAX      Integer32
    MAX-ACCESS  read-only
    STATUS      current
    DESCRIPTION
        "
        This object contains the current number of local users.
        "
    ::= { hh3cUserObjects 4 }

-- hh3cUserIndexIndicator========================================================
hh3cUserIndexIndicator OBJECT-TYPE
    SYNTAX      Integer32
    MAX-ACCESS  read-only
    STATUS      current
    DESCRIPTION
        "
        This object contains an appropriate value to
        be used for hh3cUserIndex when creating entries in the
        hh3cUserInfoTable. The value 0 indicates that no unassigned
        entries are available. To obtain the
        hh3cUserIndex value for a new
        entry, the manager issues a management
        protocol retrieval operation to obtain the
        current value of this object.  After each
        retrieval, the agent should modify the value
        to the next unassigned index.
        After a manager retrieves a value the agent will
        determine through its local policy when this index
        value will be made available for reuse.
        "
    ::= { hh3cUserObjects 5 }

END
