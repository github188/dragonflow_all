-- ============================================================================
-- Copyright (C) 2003 by  HUAWEI-3COM TECHNOLOGIES. All rights reserved.
--
-- Description: this mib will maintain the products mib oid and management
--              properties root node for Huawei-3Com products
--
-- Reference:  original from huawei-oid-mib and huawei-datacomm-oid-mib
-- Version: V1.00
-- History:
--   V1.00 2006-04-19 created by longyin
-- ============================================================================
HH3C-OID-MIB DEFINITIONS ::= BEGIN
    IMPORTS
        enterprises
            FROM RFC1155-SMI;

-- Object under .enterprises
    hh3c OBJECT IDENTIFIER ::= { enterprises 25506 }
    
-- Object under .enterprises.hh3c
    hh3cProductId OBJECT IDENTIFIER ::= { hh3c 1 }

END
