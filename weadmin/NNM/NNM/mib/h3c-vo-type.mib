-- ==========================================================================
-- Copyright (C) 2004 by Huawei 3Com Technologies. All rights reserved.
--
-- Description: The purpose of this MIB file is to provide the type 
--              declaration used for voice module.
--
-- Reference:
-- ==========================================================================
H3C-VO-TYPE-MIB DEFINITIONS ::= BEGIN
	

--======================================
--          Type declaration
--======================================
     
    CodecType ::= INTEGER
        {
        g711a(1),
        g711u(2),
        g723r53(3),
        g723r63(4),
        g729r8(5),
        g729a(6),
        g726r16(7),
        g726r24(8),
        g726r32(9),
        g726r40(10)
        }

	
END
