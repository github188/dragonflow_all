-- =================================================================
-- Copyright (C) 2002 by H3C TECHNOLOGIES.  All rights reserved.
--
-- Description: This file describes the H3C MIB implementation
--              of sending some traps.
-- Reference: H3C enterprise MIB
-- =================================================================
HH3C-TRAP-MIB DEFINITIONS ::= BEGIN

    IMPORTS
        hh3cCommon
            FROM HH3C-OID-MIB
        ifIndex,ifDescr
            FROM IF-MIB
        Integer32, Unsigned32, OBJECT-TYPE,
        MODULE-IDENTITY, NOTIFICATION-TYPE
            FROM SNMPv2-SMI;

    hh3cTrap MODULE-IDENTITY
        LAST-UPDATED "200501251354Z"        -- January 25, 2005 at 13:54 GMT
        ORGANIZATION
            "Hangzhou H3C Tech. Co., Ltd."
        CONTACT-INFO
            "Platform Team Hangzhou H3C Tech. Co., Ltd.
            Hai-Dian District Beijing P.R. China
            http://www.h3c.com
            Zip:100085
            "
        DESCRIPTION
            "This MIB is applicable to routers, switches and other products.

            Some objects in this may be used only for some specific products,
            so users should refer to the related documents to acquire more
            detail information.
            "
        REVISION "200501251354Z"        -- January 25, 2005 at 13:54 GMT
        DESCRIPTION
            "The initial revision of this MIB module."
        ::= { hh3cCommon 38 }


--
-- Node definitions
--
    hh3cTableGroup OBJECT IDENTIFIER ::= { hh3cTrap 1 }

-- Describe objects for MAC table
    hh3cMacTabStatGroup OBJECT IDENTIFIER ::= { hh3cTableGroup 1 }

    hh3cMacTabTrapEnable OBJECT-TYPE
        SYNTAX INTEGER{
                        enable(1),
                        disable(2)
                        }
        MAX-ACCESS read-write
        STATUS current
        DESCRIPTION
            "Indicates whether hh3cMacTabFullTrap and
            hh3cMacTabAlmostFullTrap traps should be generated
            when the MAC table is filled."
        DEFVAL { enable }
        ::= { hh3cMacTabStatGroup 1 }

    hh3cMacTabTrapInterval OBJECT-TYPE
        SYNTAX Integer32 (30..3600)
        UNITS "seconds"
        MAX-ACCESS read-write
        STATUS current
        DESCRIPTION
            "Definition of the minimum interval between two
            traps which occur when the MAC table is full or
            two traps which occur when the MAC table is almost full."
        DEFVAL { 30 }
        ::= { hh3cMacTabStatGroup 2 }

    hh3cMacTabTrapInfo OBJECT IDENTIFIER ::= { hh3cMacTabStatGroup 3 }

    hh3cMacTabLen OBJECT-TYPE
        SYNTAX Integer32
        MAX-ACCESS accessible-for-notify
        STATUS current
        DESCRIPTION
            "The length of the MAC table."
        ::= { hh3cMacTabTrapInfo 1 }

    hh3cMacTabTrap OBJECT IDENTIFIER ::= { hh3cMacTabStatGroup 4 }

    hh3cMacTabFullTrap NOTIFICATION-TYPE
            OBJECTS { hh3cMacTabLen }
            STATUS current
            DESCRIPTION
                "Send this trap when the MAC table is filled.  The
                interval between two traps generated should be longer
                than hh3cMacTabTrapInterval."
            ::= { hh3cMacTabTrap 1 }

    hh3cMacTabAlmostFullTrap NOTIFICATION-TYPE
            STATUS current
            DESCRIPTION
                "Send this trap when the MAC table is almost full.  The
                interval between two traps generated should be longer
                than hh3cMacTabTrapInterval."
            ::= { hh3cMacTabTrap 2 }

-- Describe objects for ARP table
    hh3cArpTabStatGroup OBJECT IDENTIFIER ::= { hh3cTableGroup 2 }

    hh3cArpTabTrapEnable OBJECT-TYPE
        SYNTAX INTEGER {
                        enable(1),
                        disable(2)
                        }
        MAX-ACCESS read-write
        STATUS current
        DESCRIPTION
            "Indicates whether hh3cArpTabFullTrap traps
            should be generated when the ARP table is filled."
        DEFVAL { enable }
        ::= { hh3cArpTabStatGroup 1 }

    hh3cArpTabTrapInterval OBJECT-TYPE
        SYNTAX Integer32 (30..3600)
        UNITS "seconds"
        MAX-ACCESS read-write
        STATUS current
        DESCRIPTION
            "Definition of the minimum interval between two traps
            which occur when the ARP table is filled."
        DEFVAL { 30 }
        ::= { hh3cArpTabStatGroup 2 }

    hh3cArpTabTrapInfo OBJECT IDENTIFIER ::= { hh3cArpTabStatGroup 3 }

    hh3cArpTabLen OBJECT-TYPE
        SYNTAX Integer32
        MAX-ACCESS accessible-for-notify
        STATUS current
        DESCRIPTION
            "The length of the ARP table."
        ::= { hh3cArpTabTrapInfo 1 }

    hh3cArpTabTrap OBJECT IDENTIFIER ::= { hh3cArpTabStatGroup 4 }

    hh3cArpTabFullTrap NOTIFICATION-TYPE
            OBJECTS { hh3cArpTabLen }
            STATUS current
            DESCRIPTION
                "Send this trap when the ARP table is filled.  The
                interval between two traps generated should be longer
                than hh3cArpTabTrapInterval."
            ::= { hh3cArpTabTrap 1 }

    hh3cArpPortDynamicEntryFullTrap NOTIFICATION-TYPE
            OBJECTS { hh3cArpTabLen, ifIndex, ifDescr }
            STATUS current
            DESCRIPTION
                 "Send this trap when the dynamic ARP number of the
                port exceeds the limitation. The object hh3cArpTabLen
                describes the limitation of the max dynamic ARP number
                of this port. The interval between two traps should be
                longer than hh3cArpTabTrapInterval."
            ::= { hh3cArpTabTrap 2 }

-- Describe objects for routing table
    hh3cRtTabStatGroup OBJECT IDENTIFIER ::= { hh3cTableGroup 3 }

    hh3cDetailRtTrapTable OBJECT-TYPE
        SYNTAX SEQUENCE OF Hh3cDetailRtTrapEntry
        MAX-ACCESS not-accessible
        STATUS current
        DESCRIPTION
            "This table contains objects to decide what kind of
            trap should be sent."
        ::= { hh3cRtTabStatGroup 1 }

    hh3cDetailRtTrapEntry OBJECT-TYPE
        SYNTAX Hh3cDetailRtTrapEntry
        MAX-ACCESS not-accessible
        STATUS current
        DESCRIPTION
            "Entry items"
        INDEX { hh3cDetailRtProType }
        ::= { hh3cDetailRtTrapTable 1 }

    Hh3cDetailRtTrapEntry ::=
        SEQUENCE {
            hh3cDetailRtProType
                INTEGER,
            hh3cDetailRtEnable
                INTEGER
        }

    hh3cDetailRtProType OBJECT-TYPE
        SYNTAX INTEGER {
            other(1),       -- none of the following

                            -- non-protocol information,
                            -- e.g., manually configured
            local(2),       -- entries
            rip(3),
            isis(4),
            ospf(5),
            bgp(6)
        }
        MAX-ACCESS accessible-for-notify
        STATUS current
        DESCRIPTION
            "The index value which uniquely identifies an entry
            in the hh3cDetailRtTrapTable."
        ::= { hh3cDetailRtTrapEntry 1 }

    hh3cDetailRtEnable OBJECT-TYPE
        SYNTAX INTEGER {
                        enable(1),
                        disable(2)
                        }
        MAX-ACCESS read-write
        STATUS current
        DESCRIPTION
            "Indicates whether hh3cDetailRtTabFullTrap traps
            should be generated when a specific routing table
            is filled."
        DEFVAL { enable }
        ::= { hh3cDetailRtTrapEntry 2 }

    hh3cRtTabTrapEnable OBJECT-TYPE
        SYNTAX INTEGER {
                        enable(1),
                        disable(2)
                        }
        MAX-ACCESS read-write
        STATUS current
        DESCRIPTION
            "Indicates whether hh3cRtTabFullTrap traps should
            be generated when the routing table is filled."
        DEFVAL { enable }
        ::= { hh3cRtTabStatGroup 2 }

    hh3cRtTabTrapInterval OBJECT-TYPE
        SYNTAX Integer32 (30..3600)
        UNITS "seconds"
        MAX-ACCESS read-write
        STATUS current
        DESCRIPTION
            "Definition of the minimum interval between two
            traps which occur when the routing table is filled."
        DEFVAL { 30 }
        ::= { hh3cRtTabStatGroup 3 }

    hh3cRtTabTrapInfo OBJECT IDENTIFIER ::= { hh3cRtTabStatGroup 4 }

    hh3cRtTabLen OBJECT-TYPE
        SYNTAX Integer32
        MAX-ACCESS accessible-for-notify
        STATUS current
        DESCRIPTION
            "The length of the routing table.  The detail
            routing tables also use the same object."
        ::= { hh3cRtTabTrapInfo 1 }

    hh3cRtTabTrap OBJECT IDENTIFIER ::= { hh3cRtTabStatGroup 5 }

    hh3cRtTabFullTrap NOTIFICATION-TYPE
            OBJECTS { hh3cRtTabLen }
            STATUS current
            DESCRIPTION
                "Send this trap when the routing table is filled.  The
                interval between two traps generated should be longer
                than hh3cRtTabTrapInterval."
            ::= { hh3cRtTabTrap 1 }

    hh3cDetailRtTabFullTrap NOTIFICATION-TYPE
            OBJECTS { hh3cDetailRtProType, hh3cRtTabLen }
            STATUS current
            DESCRIPTION
                "Send this trap when the detail routing table is filled.  The
                interval between two traps generated should be longer than
                hh3cRtTabTrapInterval."
            ::= { hh3cRtTabTrap 2 }

-- Describe objects for multicast table
    hh3cMulticastTabStatGroup OBJECT IDENTIFIER ::= { hh3cTableGroup 4 }

    hh3cMulticastTabTrapEnable OBJECT-TYPE
        SYNTAX INTEGER {
                        enable(1),
                        disable(2)
                        }
        MAX-ACCESS read-write
        STATUS current
        DESCRIPTION
            "Indicates whether hh3cMulticastTabFullTrap traps
            should be generated when the multicast table is filled."
        DEFVAL { enable }
        ::= { hh3cMulticastTabStatGroup 1 }

    hh3cMulticastTabTrapInterval OBJECT-TYPE
        SYNTAX Integer32 (30..3600)
        UNITS "seconds"
        MAX-ACCESS read-write
        STATUS current
        DESCRIPTION
            "Definition of the minimum interval between two traps
            which occur when the multicast table is filled."
        DEFVAL { 30 }
        ::= { hh3cMulticastTabStatGroup 2 }

    hh3cMulticastTabTrapInfo OBJECT IDENTIFIER ::= { hh3cMulticastTabStatGroup 3 }

    hh3cMulticastTabType OBJECT-TYPE
        SYNTAX INTEGER {
                        lay2(1),
                        lay3(2)
                        }
        MAX-ACCESS accessible-for-notify
        STATUS current
        DESCRIPTION
            "Defining the type of the multicast table, layer2 or layer3."
        ::= { hh3cMulticastTabTrapInfo 1 }

    hh3cMulticastTabLen OBJECT-TYPE
        SYNTAX Integer32
        MAX-ACCESS accessible-for-notify
        STATUS current
        DESCRIPTION
            "The length of the multicast table."
        ::= { hh3cMulticastTabTrapInfo 2 }

    hh3cMulticastTabTrap OBJECT IDENTIFIER ::= { hh3cMulticastTabStatGroup 4 }

    hh3cMulticastTabFullTrap NOTIFICATION-TYPE
            OBJECTS { hh3cMulticastTabType, hh3cMulticastTabLen }
            STATUS current
            DESCRIPTION
                "Send this trap when the multicast table is filled.  The
                interval between two traps generated should be longer
                than hh3cMulticastTabTrapInterval."
            ::= { hh3cMulticastTabTrap 1 }


-- Describe objects for Neighbor table
    hh3cNdTabStatGroup OBJECT IDENTIFIER ::= { hh3cTableGroup 5 }

    hh3cNdTabTrapEnable OBJECT-TYPE
        SYNTAX INTEGER {
                        enable(1),
                        disable(2)
                        }
        MAX-ACCESS read-write
        STATUS current
        DESCRIPTION
            "Indicates whether hh3cNdTabFullTrap traps
            should be generated when the ND table is filled."
        DEFVAL { enable }
        ::= { hh3cNdTabStatGroup 1 }

    hh3cNdTabTrapInterval OBJECT-TYPE
        SYNTAX Integer32 (30..3600)
        UNITS "seconds"
        MAX-ACCESS read-write
        STATUS current
        DESCRIPTION
            "Definition of the minimum interval between two traps
            which occur when the ND table is filled."
        DEFVAL { 30 }
        ::= { hh3cNdTabStatGroup 2 }

    hh3cNdTabTrapInfo OBJECT IDENTIFIER ::= { hh3cNdTabStatGroup 3 }

    hh3cNdTabLen OBJECT-TYPE
        SYNTAX Integer32
        MAX-ACCESS accessible-for-notify
        STATUS current
        DESCRIPTION
            "The length of the ND table."
        ::= { hh3cNdTabTrapInfo 1 }

    hh3cNdTabTrap OBJECT IDENTIFIER ::= { hh3cNdTabStatGroup 4 }

    hh3cNdTabFullTrap NOTIFICATION-TYPE
            OBJECTS { hh3cNdTabLen }
            STATUS current
            DESCRIPTION
                "Send this trap when the ND table is filled.  The
                interval between two traps generated should be longer
                than hh3cNdTabTrapInterval."
            ::= { hh3cNdTabTrap 1 }

END
