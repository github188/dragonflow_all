-- =============================================================
-- Copyright (C) 2007 by H3C TECHNOLOGIES. All rights reserved.
--
-- Description: E1T1VI MIB
-- Reference: None
-- =============================================================
HH3C-E1T1VI-MIB DEFINITIONS ::= BEGIN
    IMPORTS
        MODULE-IDENTITY, OBJECT-TYPE, Integer32
            FROM SNMPv2-SMI
        ifIndex
            FROM RFC1213-MIB
        hh3cCommon
            FROM HH3C-OID-MIB;


-- =============================================================
-- E1T1VI Module
-- =============================================================
hh3cE1T1VI MODULE-IDENTITY
    LAST-UPDATED    "200704051542Z"         -- Apr. 5, 2007 at 00:00 GMT
    ORGANIZATION
        "Hangzhou H3C Tech. Co., Ltd."
    CONTACT-INFO
        "Platform Team Hangzhou H3C Tech. Co., Ltd.
        Hai-Dian District Beijing P.R. China
        http://www.h3c.com
        Zip:100085
        "
    DESCRIPTION
        "This MIB provides E1/T1 voice interface information that are
        excluded by RFC 1213 and RFC 2233"
    REVISION        "200704051542Z"
    DESCRIPTION
        "Initial version of this MIB module."
    ::= { hh3cCommon 76 }


hh3cE1T1VITable OBJECT-TYPE
    SYNTAX      SEQUENCE OF Hh3cE1T1VIEntry
    MAX-ACCESS  not-accessible
    STATUS      current
    DESCRIPTION
        "This table contains E1/T1 voice interface information, 
        such as the total number of using time slot."
    ::= { hh3cE1T1VI 1 }

hh3cE1T1VIEntry OBJECT-TYPE
    SYNTAX      Hh3cE1T1VIEntry
    MAX-ACCESS  not-accessible
    STATUS      current
    DESCRIPTION
        "This entry contains E1/T1 voice interface information.
        The index of this Entry is ifIndex defined in ifTable
        of RFC1213-MIB."
    INDEX
        {
            ifIndex
        }
    ::= { hh3cE1T1VITable 1 }

Hh3cE1T1VIEntry ::= SEQUENCE
    {
        hh3cE1T1VIUsingTimeslots    Integer32
    }

hh3cE1T1VIUsingTimeslots OBJECT-TYPE
    SYNTAX      Integer32
    MAX-ACCESS  read-only
    STATUS      current
    DESCRIPTION
        "The total number of using time slot on this interface."
    ::= { hh3cE1T1VIEntry 1 }

END
