-- ==================================================================
-- Copyright (C) 2004 by  H3C TECHNOLOGIES. All rights reserved.
--
-- Description: H3C Lan Switch Domain MIB
-- Reference:
-- ==================================================================
HH3C-DOMAIN-MIB DEFINITIONS ::= BEGIN
    IMPORTS
        hh3cCommon
            FROM HH3C-OID-MIB
        OBJECT-GROUP, MODULE-COMPLIANCE
            FROM SNMPv2-CONF
        Integer32, Counter32, OBJECT-TYPE, MODULE-IDENTITY, NOTIFICATION-TYPE
            FROM SNMPv2-SMI
        InetAddressType, InetAddress
            FROM INET-ADDRESS-MIB
        RowStatus, TruthValue
            FROM SNMPv2-TC;

    hh3cDomain MODULE-IDENTITY
        LAST-UPDATED "200503230000Z"            -- March 23, 2005 at 00:00 GMT
        ORGANIZATION
            "Hangzhou H3C Tech. Co., Ltd."
        CONTACT-INFO
            "Platform Team Hangzhou H3C Tech. Co., Ltd.
            Hai-Dian District Beijing P.R. China
            http://www.h3c.com
            Zip:100085
            "
        DESCRIPTION
            "The MIB module is used for managing domain."
    ::= { hh3cCommon 46 }

    Hh3cModeOfDomainScheme ::= TEXTUAL-CONVENTION
        STATUS current
        DESCRIPTION
        "The scheme mode of the domain.
        none: indicates the domain has no scheme.
        local:indicates the domain will use local-server as a scheme.
        radius:indicates the domain will use radius scheme.
        tacacs:indicates the domain will use tacacs scheme."
        SYNTAX INTEGER
        {
            none(1),
            local(2),
            radius(3),
            tacacs(4)
        }

    Hh3cAAATypeDomainScheme ::= TEXTUAL-CONVENTION
        STATUS current
        DESCRIPTION
        "The service type of the server."
        SYNTAX INTEGER
        {
            accounting(1),
            authentication(2),
            authorization(3),
            none(4)
        }

  Hh3cAccessModeofDomainScheme ::= TEXTUAL-CONVENTION
        STATUS current
        DESCRIPTION
        "The access mode of the domain."
        SYNTAX INTEGER
        {
            default(1),
            login(2),
            lanAccess(3),
            portal(4),
            ppp(5),
            gcm(6),
            dvpn(7),
            dhcp(8),
            voice(9),
            superauthen(10),
            command(11)
        }

    hh3cDomainControl OBJECT IDENTIFIER ::= { hh3cDomain 1 }

    hh3cDomainDefault OBJECT-TYPE
        SYNTAX      OCTET STRING (SIZE (1..128))
        MAX-ACCESS  read-write
        STATUS      current
        DESCRIPTION
        "Specifies default domain on the equipment.  Default value is 'system'."
    ::=  { hh3cDomainControl 1 }


    hh3cDomainTables OBJECT IDENTIFIER ::= { hh3cDomain 2 }

    hh3cDomainInfoTable OBJECT-TYPE
        SYNTAX  SEQUENCE OF Hh3cDomainInfoEntry
        MAX-ACCESS  not-accessible
        STATUS  current
        DESCRIPTION
        "The (conceptual) table listing the domains."
    ::= { hh3cDomainTables 1 }

    hh3cDomainInfoEntry OBJECT-TYPE
        SYNTAX  Hh3cDomainInfoEntry
        MAX-ACCESS  not-accessible
        STATUS  current
        DESCRIPTION
        "An entry (conceptual row) representing a domain."
        INDEX { hh3cDomainName }
    ::= { hh3cDomainInfoTable 1 }

    Hh3cDomainInfoEntry ::= SEQUENCE {
        hh3cDomainName                   OCTET STRING,
        hh3cDomainState                  INTEGER,
        hh3cDomainMaxAccessNum           Integer32,
        hh3cDomainVlanAssignMode         INTEGER,
        hh3cDomainIdleCutEnable          TruthValue,
        hh3cDomainIdleCutMaxTime         Integer32,
        hh3cDomainIdleCutMinFlow         Integer32,
        hh3cDomainMessengerEnable        TruthValue,
        hh3cDomainMessengerLimitTime     Integer32,
        hh3cDomainMessengerSpanTime      Integer32,
        hh3cDomainSelfServiceEnable      TruthValue,
        hh3cDomainSelfServiceURL         OCTET STRING,
        hh3cDomainAccFailureAction       INTEGER,
        hh3cDomainRowStatus              RowStatus }

    hh3cDomainName   OBJECT-TYPE
        SYNTAX  OCTET STRING (SIZE (1..128))
        MAX-ACCESS  not-accessible
        STATUS  current
        DESCRIPTION
        "An index uniquely identifies a domain. "
    ::= { hh3cDomainInfoEntry  1 }

    hh3cDomainState   OBJECT-TYPE
        SYNTAX INTEGER
        {
            active(1),
            block(2)
        }
        MAX-ACCESS  read-create
        STATUS  current
        DESCRIPTION
        "The state of the domain, which reflects whether the domain is active.
        Default value is active."
    ::= { hh3cDomainInfoEntry  2 }

    hh3cDomainMaxAccessNum   OBJECT-TYPE
        SYNTAX Integer32
        MAX-ACCESS  read-create
        STATUS  current
        DESCRIPTION
        "The maximum number which the domain allows to access.  If the value
        is set to 0, the access limit will be disabled."
    ::= { hh3cDomainInfoEntry  3 }

    hh3cDomainVlanAssignMode   OBJECT-TYPE
        SYNTAX INTEGER
        {
            integer(1),
            string(2)
        }
        MAX-ACCESS  read-create
        STATUS  current
        DESCRIPTION
        "The vlan assignment mode.  The mode SHOULD be the same as the mode of
        corresponding server.
        1 (integer) - Integer Vlan assignment mode.
        2 (string)  - String Vlan assignment mode.
        The default value is integer."
    ::= { hh3cDomainInfoEntry  4 }

    hh3cDomainIdleCutEnable   OBJECT-TYPE
        SYNTAX TruthValue
        MAX-ACCESS  read-create
        STATUS  current
        DESCRIPTION
        "The idle cut control.  Setting this attribute to true, the connection will be
        cut when the flow is less than hh3cDomainIdleCutMinFlow and lasts
        hh3cDomainIdleCutMaxTime. Default value is false."
    ::= { hh3cDomainInfoEntry  5 }

    hh3cDomainIdleCutMaxTime   OBJECT-TYPE
        SYNTAX Integer32(1..120)
        MAX-ACCESS  read-create
        STATUS  current
        DESCRIPTION
        "The maximal time of idle-cut.  The unit is minute.  If the value of
        hh3cDomainIdleCutEnable is false, the value of hh3cDomainIdleCutMaxTime
        is meaningless."
    ::= { hh3cDomainInfoEntry  6 }

    hh3cDomainIdleCutMinFlow   OBJECT-TYPE
        SYNTAX Integer32(1..10240000)
        MAX-ACCESS  read-create
        STATUS  current
        DESCRIPTION
        "The minimal flow of idle-cut.  The unit is byte. If the value of
        hh3cDomainIdleCutEnable is false, the value of hh3cDomainIdleCutMinFlow
        is meaningless."
    ::= { hh3cDomainInfoEntry  7 }

    hh3cDomainMessengerEnable   OBJECT-TYPE
        SYNTAX TruthValue
        MAX-ACCESS  read-create
        STATUS  current
        DESCRIPTION
        "The messenger service control.  If set hh3cDomainMessengerEnable to true,
        hh3cDomainMessengerLimitTime and hh3cDomainMessengerSpanTime must be
        set to valid values.  Default value is false."
    ::= { hh3cDomainInfoEntry  8 }

    hh3cDomainMessengerLimitTime   OBJECT-TYPE
        SYNTAX Integer32(1..60)
        MAX-ACCESS  read-create
        STATUS  current
        DESCRIPTION
        "The messenger service limit time.  The unit is minute.  If the value of
        hh3cDomainMessengerEnable is false, the value of hh3cDomainMessengerLimitTime
        is meaningless."
    ::= { hh3cDomainInfoEntry  9 }

    hh3cDomainMessengerSpanTime   OBJECT-TYPE
        SYNTAX Integer32(5..60)
        MAX-ACCESS  read-create
        STATUS  current
        DESCRIPTION
        "The messenger service span time.  The unit is minute.
        It must be a multiple of 5.  If the value of hh3cDomainMessengerEnable is false,
        the value of hh3cDomainMessengerSpanTime is meaningless."
    ::= { hh3cDomainInfoEntry  10 }

    hh3cDomainSelfServiceEnable   OBJECT-TYPE
        SYNTAX TruthValue
        MAX-ACCESS  read-create
        STATUS  current
        DESCRIPTION
        "The self service control.  If set hh3cDomainSelfServiceEnable to true,
        hh3cDomainSelfServiceURL must be set to a valid value.
        Default value is FALSE."
    ::= { hh3cDomainInfoEntry  11 }

    hh3cDomainSelfServiceURL   OBJECT-TYPE
        SYNTAX OCTET STRING (SIZE (1..64))
        MAX-ACCESS  read-create
        STATUS  current
        DESCRIPTION
        "Self-service URL(Uniform Resource Locator) of the domain."
    ::= { hh3cDomainInfoEntry  12 }

    hh3cDomainAccFailureAction   OBJECT-TYPE
        SYNTAX INTEGER
        {
            ignore(1),
            reject(2)
        }
        MAX-ACCESS  read-create
        STATUS  current
        DESCRIPTION
        "Defines the action that authentication should be taken if
        authentication succeeds but the associated accounting start
        fails.
        1 (ignore) - treat as authentication success; ignore
            accounting start failure.
        2 (reject) - treat as authentication failed if
            corresponding accounting start fails.
        Default value is reject."
    ::= { hh3cDomainInfoEntry  13 }

    hh3cDomainRowStatus   OBJECT-TYPE
        SYNTAX   RowStatus
        MAX-ACCESS  read-create
        STATUS   current
        DESCRIPTION
        "This object is responsible for managing the creation, deletion and modification
        of rows, which supports active status and CreateAndGo, Destroy operation. To destroy
        an existent row, the domain of the row MUST NOT be used by user."
    ::= { hh3cDomainInfoEntry 14 }


    -- ----------------------------------------------------------------------
    -- Scheme Table
    -- ----------------------------------------------------------------------
    hh3cDomainSchemeTable OBJECT-TYPE
        SYNTAX  SEQUENCE OF Hh3cDomainSchemeEntry
        MAX-ACCESS  not-accessible
        STATUS  current
        DESCRIPTION
        "The (conceptual) table listing schemes of all domains."
    ::= { hh3cDomainTables 2 }

    hh3cDomainSchemeEntry OBJECT-TYPE
        SYNTAX  Hh3cDomainSchemeEntry
        MAX-ACCESS  not-accessible
        STATUS  current
        DESCRIPTION
        "An entry (conceptual row) representing an IP pool of a domain"
        INDEX { hh3cDomainName, hh3cDomainSchemeIndex }
    ::= { hh3cDomainSchemeTable 1 }

    Hh3cDomainSchemeEntry ::= SEQUENCE {
        hh3cDomainSchemeIndex            Integer32,
        hh3cDomainSchemeMode             Hh3cModeOfDomainScheme,
        hh3cDomainAuthSchemeName         OCTET STRING,
        hh3cDomainAcctSchemeName         OCTET STRING,
        hh3cDomainSchemeRowStatus        RowStatus,
        hh3cDomainSchemeAAAType          Hh3cAAATypeDomainScheme,
        hh3cDomainSchemeAAAName          OCTET STRING,
        hh3cDomainSchemeAccessMode       Hh3cAccessModeofDomainScheme

        }

    hh3cDomainSchemeIndex   OBJECT-TYPE
        SYNTAX Integer32
        MAX-ACCESS  not-accessible
        STATUS  current
        DESCRIPTION
        "The scheme index of domain, which is an identifier of a domain scheme."
    ::= { hh3cDomainSchemeEntry  1 }

    hh3cDomainSchemeMode   OBJECT-TYPE
        SYNTAX Hh3cModeOfDomainScheme
        MAX-ACCESS  read-create
        STATUS  current
        DESCRIPTION
        "The scheme mode of the domain.  Setting hh3cDomainSchemeMode to none(1) indicates
        the domain has none scheme.  Setting hh3cDomainSchemeMode to local(2) indicates the
        domain will use local-server as a scheme.  Setting hh3cDomainSchemeMode to radius(3)
        or tacacs(4) indicates the domain will use radius or tacacs scheme.  If set
        hh3cDomainSchemeMode to radius(3) or tacacs(4), hh3cDomainAuthSchemeName and
        hh3cDomainAcctSchemeName must be set to valid values.  And if hh3cDomainSchemeMode is
        set to none(1) or local(2), the value of hh3cDomainAuthSchemeName and hh3cDomainAcctSchemeName
        will be ignored."
    ::= { hh3cDomainSchemeEntry  2 }

    hh3cDomainAuthSchemeName   OBJECT-TYPE
        SYNTAX OCTET STRING (SIZE (0..32))
        MAX-ACCESS  read-create
        STATUS  current
        DESCRIPTION
        "The authentication scheme name of domain.  If hh3cDomainSchemeMode is set to radius
        or tacacs, the hh3cDomainAuthSchemeName must be configured with a valid value."
    ::= { hh3cDomainSchemeEntry  3 }

    hh3cDomainAcctSchemeName   OBJECT-TYPE
        SYNTAX OCTET STRING (SIZE (0..32))
        MAX-ACCESS  read-create
        STATUS  current
        DESCRIPTION
        "The accounting scheme name of the domain. If hh3cDomainSchemeMode is set to radius
        or tacacs, the hh3cDomainAcctSchemeName must be configured with a valid value."
    ::= { hh3cDomainSchemeEntry  4 }

    hh3cDomainSchemeRowStatus   OBJECT-TYPE
        SYNTAX RowStatus
        MAX-ACCESS  read-create
        STATUS  current
        DESCRIPTION
        "This object is responsible for managing the creation, deletion and modification
        of rows, which supports active status and createAndGo, destroy operation. To
        create a new row, hh3cDomainSchemeMode must be specified. To destroy an existent
        row, the scheme of the row MUST NOT be used by user."
    ::= { hh3cDomainSchemeEntry  5 }

    hh3cDomainSchemeAAAType    OBJECT-TYPE
        SYNTAX     Hh3cAAATypeDomainScheme
        MAX-ACCESS  read-create
        STATUS  current
        DESCRIPTION
        "Service Type of the server."
   ::= { hh3cDomainSchemeEntry  6 }

    hh3cDomainSchemeAAAName       OBJECT-TYPE
         SYNTAX      OCTET STRING(SIZE (0..32))
         MAX-ACCESS  read-create
         STATUS  current
         DESCRIPTION
         "The scheme name of the domain, whether the scheme represents accounting,
          authentication or authorization references the object hh3cDomainSchemeAAAType.
          The value of the object must be valid if the value of hh3cDomainSchemeMode
          is radius or tacacs, the value of the object will be ignored if the value
          of hh3cDomainSchemeMode is none or local. If the domain has no scheme,
          there will be a null string. If this object is supported, the objects
          hh3cDomainAuthSchemeName and hh3cDomainAcctSchemeName will be ignored."
    ::= { hh3cDomainSchemeEntry  7 }

    hh3cDomainSchemeAccessMode    OBJECT-TYPE
         SYNTAX      Hh3cAccessModeofDomainScheme
         MAX-ACCESS  read-create
         STATUS  current
         DESCRIPTION
         "The access mode of the domain scheme."
    ::= { hh3cDomainSchemeEntry  8 }

    -- ----------------------------------------------------------------------
    -- IP pool Table
    -- ----------------------------------------------------------------------
    hh3cDomainIpPoolTable OBJECT-TYPE
        SYNTAX  SEQUENCE OF Hh3cDomainIpPoolEntry
        MAX-ACCESS  not-accessible
        STATUS  current
        DESCRIPTION
        "The (conceptual) table listing IP pools of all domains."
    ::= { hh3cDomainTables 3 }

    hh3cDomainIpPoolEntry OBJECT-TYPE
        SYNTAX  Hh3cDomainIpPoolEntry
        MAX-ACCESS  not-accessible
        STATUS  current
        DESCRIPTION
        "An entry (conceptual row) representing an IP pool of a domain."
        INDEX { hh3cDomainName, hh3cDomainIpPoolNum }
    ::= { hh3cDomainIpPoolTable 1 }

    Hh3cDomainIpPoolEntry ::= SEQUENCE {
        hh3cDomainIpPoolNum              Integer32,
        hh3cDomainIpPoolLowIpAddrType    InetAddressType,
        hh3cDomainIpPoolLowIpAddr        InetAddress,
        hh3cDomainIpPoolLen              Integer32,
        hh3cDomainIpPoolRowStatus        RowStatus }


    hh3cDomainIpPoolNum   OBJECT-TYPE
        SYNTAX   Integer32(0..99)
        MAX-ACCESS  not-accessible
        STATUS   current
        DESCRIPTION
        "The number of IP pool, which is an identifier of an IP pool."
    ::= { hh3cDomainIpPoolEntry 1 }


    hh3cDomainIpPoolLowIpAddrType   OBJECT-TYPE
        SYNTAX   InetAddressType
        MAX-ACCESS  read-create
        STATUS   current
        DESCRIPTION
        "The low IP addresses type (IPv4 or IPv6) of IP pool."
    ::= { hh3cDomainIpPoolEntry 2 }


    hh3cDomainIpPoolLowIpAddr   OBJECT-TYPE
        SYNTAX   InetAddress
        MAX-ACCESS  read-create
        STATUS   current
        DESCRIPTION
        "The low IP address of IP pool."
    ::= { hh3cDomainIpPoolEntry 3 }


    hh3cDomainIpPoolLen   OBJECT-TYPE
        SYNTAX   Integer32
        MAX-ACCESS  read-create
        STATUS   current
        DESCRIPTION
        "The length of IP pool.  Default value is 1."
    ::= { hh3cDomainIpPoolEntry 4 }

   hh3cDomainIpPoolRowStatus   OBJECT-TYPE
        SYNTAX   RowStatus
        MAX-ACCESS  read-create
        STATUS   current
        DESCRIPTION
        "This object is responsible for managing the creation, deletion and modification
        of rows, which supports active status and CreateAndGo, Destroy operation.  To
        create a new row, hh3cDomainIpPoolNum and hh3cDomainIpPoolLowIpAddr must be specified.
        To destroy an existent row, the IP pool of this row MUST NOT be used by user."
    ::= { hh3cDomainIpPoolEntry 5 }
END
