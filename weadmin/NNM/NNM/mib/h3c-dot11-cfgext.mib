-- =============================================================================
-- Copyright (C) 2006-2007 by HUAWEI-3COM TECHNOLOGIES.  All rights reserved.
--
-- Description:
--   The file defines a MIB to provide WLAN configuration extended.
-- Reference:
-- =============================================================================
H3C-DOT11-CFGEXT-MIB DEFINITIONS ::= BEGIN

IMPORTS
        TruthValue
    FROM SNMPv2-TC
        MODULE-IDENTITY,
        OBJECT-TYPE,
        Integer32
    FROM SNMPv2-SMI
        h3cDot11
    FROM H3C-DOT11-REF-MIB;

h3cDot11CFGEXT MODULE-IDENTITY
    LAST-UPDATED "200704252000Z"            -- Apr. 25, 2007 at 20:00 GMT
    ORGANIZATION
        "HUAWEI-3COM Technologies Co., Ltd."
    CONTACT-INFO
        "Platform Team HUAWEI-3COM Technologies Co., Ltd.
         Hai-Dian District Beijing P.R. China
         Http://www.huawei-3com.com
         Zip:100085"
    DESCRIPTION
        "This MIB provides information for WLAN configuration extended.
        The h3c-dot11-cfg.mib define MIB objects for WLAN basic configuration,
        while this MIB will define MIB objects for load balance these kinds
        feature.

        GLOSSARY

        IEEE 802.11
        Standard to encourage interoperability among
        wireless networking equipment.

        Access point (AP)
        Transmitter/receiver (transceiver) device
        that commonly connects and transports data
        between a wireless network and a wired network.

        Access control (AC)
        To control and manage multi-APs, it will bridge
        wireless and wired network.

        Fat AP
        Applied in the home, SOHO and so on, and it could
        work independently without help from AC.

        Fit AP
        Applied in the enterprise environment, it will work
        under the control and management from AC.

        Control And Provisioning of Wireless Access Points Protocol
        The short name of protocol is CAPWAP. AC will control
        and manage AP by CAPWAP tunnel protocol defined by IETF.
        Also, a data tunnel will be set up between AC and AP.

        BSS
        IEEE 802.11 Basic Service Set (Radio Cell).  The
        BSS of an AP comprises of the stations directly
        associating with the AP.

        Radio
        The chip set to receive and send wireless signal.

        Association
        The service used to establish access point
        or station mapping and enable station invocation
        of the distribution system services.
        (Wireless clients attempt to connect to
        access points.)

        Basic Rate
        A data rate that is mandatory for client
        devices to support in order for them to achieve
        successful association.

        MSDU
        MAC Service Data Unit, it is frame format defined by
        802.11.

        TU
        It is 1,024 microseconds (ms), which is about 1
        millisecond.

        AKM
        The authentication and key management method defined by
        802.11i, and which includes 802.1x and pre-shared key."

    REVISION "200704252000Z"        -- Apr. 25, 2007 at 20:00 GMT
    DESCRIPTION
        "The initial revision of this MIB module."
    ::= { h3cDot11 6 }

-- *****************************************************************************
-- *  Major sections
-- *****************************************************************************
--  Load Balancing Group
--  DEFINED AS "The group to provide the configuration information
--  for load balancing feature.
h3cDot11LoadBalance OBJECT IDENTIFIER   ::= { h3cDot11CFGEXT 1 }
h3cDot11LBGlobalGroup OBJECT IDENTIFIER ::= { h3cDot11LoadBalance 1 }

-- *****************************************************************************
-- *  h3cDot11LBGlobalGroup Definition
-- *****************************************************************************
h3cDot11LoadBalanceTrafficEnable OBJECT-TYPE
    SYNTAX      TruthValue
    MAX-ACCESS  read-write
    STATUS      current
    DESCRIPTION
        "Represents whether enable load balancing according to station
        traffic."
    ::= { h3cDot11LBGlobalGroup 1 }

h3cDot11LoadBalanceTrafficThres OBJECT-TYPE
    SYNTAX      Integer32
    MAX-ACCESS  read-write
    STATUS      current
    DESCRIPTION
        "Represents the threshold value for Traffic based load balancing."
    ::= { h3cDot11LBGlobalGroup 2 }

h3cDot11LoadBalanceSessionEnable OBJECT-TYPE
    SYNTAX      TruthValue
    MAX-ACCESS  read-write
    STATUS      current
    DESCRIPTION
        "Represents whether enable load balancing according to station
        session number."
    ::= { h3cDot11LBGlobalGroup 3 }

h3cDot11LoadBalanceSessionThres OBJECT-TYPE
    SYNTAX      Integer32
    MAX-ACCESS  read-write
    STATUS      current
    DESCRIPTION
        "Represents the threshold value for session number based
        load balancing."
    ::= { h3cDot11LBGlobalGroup 4 }
-- *****************************************************************************
-- *  End of h3cDot11LBGlobalGroup Definition
-- *****************************************************************************
END
