-- =============================================================
-- Copyright (C) 2002 by H3C TECHNOLOGIES. All rights reserved.
--
-- Description: 
-- Reference:  extension of RFC 1213 and RFC 2233
-- =============================================================
HH3C-T1-MIB DEFINITIONS ::= BEGIN
 
IMPORTS
        MODULE-IDENTITY,
        OBJECT-TYPE,
        Integer32,
        Counter32
                FROM SNMPv2-SMI
        MODULE-COMPLIANCE,
        OBJECT-GROUP
                FROM SNMPv2-CONF
        ifIndex
                FROM RFC1213-MIB
        hh3cCommon
                FROM HH3C-OID-MIB;
                

                
-- =============================================================
-- T1 Module
-- =============================================================              
hh3cT1    MODULE-IDENTITY
        LAST-UPDATED    "200412011436Z"
        ORGANIZATION
            "Hangzhou H3C Tech. Co., Ltd."
        CONTACT-INFO
            "Platform Team Hangzhou H3C Tech. Co., Ltd.
            Hai-Dian District Beijing P.R. China
            http://www.h3c.com
            Zip:100085
            "
        DESCRIPTION
             "This MIB provides T1 interface information that are 
             excluded by RFC 1213 and RFC 2233"
        REVISION        "200412011436Z"
        DESCRIPTION
                "Initial version of this MIB module."
        ::= { hh3cCommon 29 }
 
 
hh3ct1InterfaceStatusTable OBJECT-TYPE
        SYNTAX      SEQUENCE OF Hh3cT1InterfaceStatusEntry
        MAX-ACCESS   not-accessible
        STATUS       current
        DESCRIPTION
         "This table contains interface packet statistics  "
        ::= { hh3cT1 1 }
 
hh3ct1InterfaceStatusEntry OBJECT-TYPE
        SYNTAX         Hh3cT1InterfaceStatusEntry
        MAX-ACCESS     not-accessible
        STATUS         current
        DESCRIPTION
         "This  entry contains interface packet statistics.
         The index of this Entry is ifIndex defined in ifTable
         of RFC1213-MIB"
        INDEX { ifIndex }
        ::= { hh3ct1InterfaceStatusTable 1 }
 
Hh3cT1InterfaceStatusEntry ::= SEQUENCE  {    
        hh3ct1InterfaceInErrs            Counter32,
        hh3ct1InterfaceInRuntsErrs	     Counter32,
        hh3ct1InterfaceInGiantsErrs	     Counter32,
        hh3ct1InterfaceInCrcErrs         Counter32,  
        hh3ct1InterfaceInAlignErrs	     Counter32,
        hh3ct1InterfaceInOverRunsErrs    Counter32,
        hh3ct1InterfaceInDribblesErrs    Counter32,
        hh3ct1InterfaceInAbortedSeqErrs  Counter32,
        hh3ct1InterfaceInNoBufferErrs    Counter32,
        hh3ct1InterfaceInFramingErrs     Counter32,
        hh3ct1InterfaceOutputErrs        Counter32,
        hh3ct1InterfaceOutUnderRunErrs   Counter32,
        hh3ct1InterfaceOutCollisonsErrs  Counter32,
        hh3ct1InterfaceOutDeferedErrs    Counter32                             
        }
        
hh3ct1InterfaceInErrs        OBJECT-TYPE
        SYNTAX          Counter32
        MAX-ACCESS      read-only
        STATUS          current
        DESCRIPTION
         "The total number of error received on this interface"
        ::= { hh3ct1InterfaceStatusEntry 1 }
 
hh3ct1InterfaceInRuntsErrs   OBJECT-TYPE
        SYNTAX          Counter32
        MAX-ACCESS      read-only
        STATUS          current
        DESCRIPTION
         "The number of Runts Error(too short packet) received on this interface"
	::= { hh3ct1InterfaceStatusEntry 2 }
 
hh3ct1InterfaceInGiantsErrs	OBJECT-TYPE
        SYNTAX          Counter32
        MAX-ACCESS      read-only
        STATUS          current
        DESCRIPTION
         "The number of Giants Error(too long packet) received on this interface"
	::= { hh3ct1InterfaceStatusEntry 3 } 
	
hh3ct1InterfaceInCrcErrs     OBJECT-TYPE
        SYNTAX          Counter32
        MAX-ACCESS      read-only
        STATUS          current
        DESCRIPTION
         "The number of CRC Error received on this interface"
	::= { hh3ct1InterfaceStatusEntry 4 }  
	
hh3ct1InterfaceInAlignErrs   OBJECT-TYPE 
        SYNTAX          Counter32
        MAX-ACCESS      read-only
        STATUS          current
        DESCRIPTION
         "The number of Align Error received on this interface"
	::= { hh3ct1InterfaceStatusEntry 5 }

hh3ct1InterfaceInOverRunsErrs OBJECT-TYPE
        SYNTAX           Counter32
        MAX-ACCESS       read-only
        STATUS          current
        DESCRIPTION
         "The number of Over Runs Error received on this interface"
	::= { hh3ct1InterfaceStatusEntry 6 }

hh3ct1InterfaceInDribblesErrs  OBJECT-TYPE
        SYNTAX            Counter32
        MAX-ACCESS  	  read-only
        STATUS            current
        DESCRIPTION
         "The number of dribble packets received"
	::= { hh3ct1InterfaceStatusEntry 7 }

hh3ct1InterfaceInAbortedSeqErrs    OBJECT-TYPE
        SYNTAX                Counter32
        MAX-ACCESS            read-only
        STATUS                current
        DESCRIPTION
         "The number of AbortedSeq Error received on this interface"
	::= { hh3ct1InterfaceStatusEntry 8 }

hh3ct1InterfaceInNoBufferErrs      OBJECT-TYPE
        SYNTAX                Counter32
        MAX-ACCESS            read-only
        STATUS                current
        DESCRIPTION
         "The number of Error (no buffer available)"
	::= { hh3ct1InterfaceStatusEntry 9 }
 
hh3ct1InterfaceInFramingErrs       OBJECT-TYPE
        SYNTAX                Counter32
        MAX-ACCESS            read-only
        STATUS                current
        DESCRIPTION
         "The number of framing Errors"
	::= { hh3ct1InterfaceStatusEntry 10 }
 
hh3ct1InterfaceOutputErrs          OBJECT-TYPE
        SYNTAX                Counter32
        MAX-ACCESS            read-only
        STATUS                current
        DESCRIPTION
         "The number of total Error transmited on this interface"
	::= { hh3ct1InterfaceStatusEntry 11 }

hh3ct1InterfaceOutUnderRunErrs     OBJECT-TYPE
        SYNTAX                Counter32
        MAX-ACCESS            read-only
        STATUS                current
        DESCRIPTION
         "The number of UnderRun Error transmited on this interface"
	::= { hh3ct1InterfaceStatusEntry 12 }

hh3ct1InterfaceOutCollisonsErrs    OBJECT-TYPE
        SYNTAX                Counter32
        MAX-ACCESS            read-only
        STATUS                current
        DESCRIPTION
         "The number of Collisions Error transmited on this interface"
	::= { hh3ct1InterfaceStatusEntry 13 }

hh3ct1InterfaceOutDeferedErrs      OBJECT-TYPE
        SYNTAX                Counter32
        MAX-ACCESS            read-only
        STATUS                current
        DESCRIPTION
         "The number of Deferred Error transmited on this interface"
	::= { hh3ct1InterfaceStatusEntry 14 }

END
