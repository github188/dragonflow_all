-- =====================================================================
-- Copyright (C) 2003 by  HUAWEI TECHNOLOGIES. All rights reserved.
--
-- Description: Huawei Timerange MIB Definition
-- Reference: Huawei Enterprise MIB
-- =====================================================================
HUAWEI-TRNG-MIB DEFINITIONS ::= BEGIN

		IMPORTS
			huaweiMgmt
			    FROM HUAWEI-3COM-OID-MIB
			OBJECT-GROUP, MODULE-COMPLIANCE
				FROM SNMPv2-CONF
			Integer32, OBJECT-TYPE, MODULE-IDENTITY
				FROM SNMPv2-SMI
			TruthValue, DateAndTime, RowStatus
				FROM SNMPv2-TC;


		hwTRNG MODULE-IDENTITY
			LAST-UPDATED "200304110000Z"		-- April 11, 2003 at 00:00 GMT
			ORGANIZATION
				"Huawei Technologies Co., Ltd."
			CONTACT-INFO
				"R&D BeiJing, Huawei Technologies co.,Ltd.
				Huawei Bld.,NO.3 Xinxi Rd.,
				Shang-Di Information Industry Base,
				Hai-Dian District Beijing P.R. China
				Zip:100085
				Http://www.huawei.com
				E-mail:support@huawei.com"
			DESCRIPTION
				"The HUAWEI-TRNG-MIB contains objects to
				Configure the system absolute and periodic time-range."
			REVISION "200304110000Z"		-- April 11, 2003 at 00:00 GMT
			DESCRIPTION
				"200304110000Z, --The initial revision of this MIB module."
			::= { huaweiDatacomm 13 }


--
-- Node definitions
--

		huaweiDatacomm OBJECT IDENTIFIER ::= { huaweiMgmt 25 }

		hwTRNGMibObjects OBJECT IDENTIFIER ::= { hwTRNG 1 }


		hwTrngCreateTimerangeTable OBJECT-TYPE
			SYNTAX SEQUENCE OF HwTrngCreateTimerangeEntry
			MAX-ACCESS not-accessible
			STATUS current
			DESCRIPTION
                              "Creat TimeRange."
			::= { hwTRNGMibObjects 1 }


		hwTrngCreateTimerangeEntry OBJECT-TYPE
			SYNTAX HwTrngCreateTimerangeEntry
			MAX-ACCESS not-accessible
			STATUS current
			DESCRIPTION
				"Define the entry of hwTrngCreateTimerangeTable"
			INDEX { hwTrngIndex }
			::= { hwTrngCreateTimerangeTable 1 }


		HwTrngCreateTimerangeEntry ::=
			SEQUENCE {
				hwTrngIndex
					Integer32,
				hwTrngName
					OCTET STRING,
				hwTrngValidFlag
					TruthValue,
				hwTrngCreateRowStatus
					RowStatus
			 }

		hwTrngIndex OBJECT-TYPE
			SYNTAX Integer32 (1..256)
			MAX-ACCESS not-accessible
			STATUS current
			DESCRIPTION
				"TimeRange's index"
			::= { hwTrngCreateTimerangeEntry 1 }


		hwTrngName OBJECT-TYPE
			SYNTAX OCTET STRING (SIZE (1..32))
			MAX-ACCESS read-create
			STATUS current
			DESCRIPTION
				"TimeRange's name"
			::= { hwTrngCreateTimerangeEntry 2 }


		hwTrngValidFlag OBJECT-TYPE
			SYNTAX TruthValue
			MAX-ACCESS read-only
			STATUS current
			DESCRIPTION
				"Valid or Invalid flag"
			::= { hwTrngCreateTimerangeEntry 3 }


		hwTrngCreateRowStatus OBJECT-TYPE
			SYNTAX RowStatus
			MAX-ACCESS read-create
			STATUS current
			DESCRIPTION
				"The status of this conceptual row.Now only realize CreateAndGo and Destroy and Active."
			::= { hwTrngCreateTimerangeEntry 4 }


		hwTrngAbsoluteTable OBJECT-TYPE
			SYNTAX SEQUENCE OF HwTrngAbsoluteEntry
			MAX-ACCESS not-accessible
			STATUS current
			DESCRIPTION
				"Creat absoluteness time item of the TimeRange"
			::= { hwTRNGMibObjects 2 }


		hwTrngAbsoluteEntry OBJECT-TYPE
			SYNTAX HwTrngAbsoluteEntry
			MAX-ACCESS not-accessible
			STATUS current
			DESCRIPTION
				"Define the entry of hwTrngAbsoluteTable"
			INDEX { hwTrngAbsoluteNameIndex, hwTrngAbsoluteSubIndex }
			::= { hwTrngAbsoluteTable 1 }


		HwTrngAbsoluteEntry ::=
			SEQUENCE {
				hwTrngAbsoluteNameIndex
					Integer32,
				hwTrngAbsoluteSubIndex
					Integer32,
				hwTimerangeAbsoluteStartTime
					DateAndTime,
				hwTimerangeAbsoluteEndTime
					DateAndTime,
				hwTimerangeAbsolueRowStatus
					RowStatus
			 }

		hwTrngAbsoluteNameIndex OBJECT-TYPE
			SYNTAX Integer32 (1..256)
			MAX-ACCESS not-accessible
			STATUS current
			DESCRIPTION
				"TimeRange's index"
			::= { hwTrngAbsoluteEntry 1 }


		hwTrngAbsoluteSubIndex OBJECT-TYPE
			SYNTAX Integer32 (1..12)
			MAX-ACCESS not-accessible
			STATUS current
			DESCRIPTION
				"SubItem's index"
			::= { hwTrngAbsoluteEntry 2 }


		hwTimerangeAbsoluteStartTime OBJECT-TYPE
			SYNTAX DateAndTime
			MAX-ACCESS read-create
			STATUS current
			DESCRIPTION
				"Start point of the timerange.The format defined like 'YYYY-MM-DD,hh:mm:0.0'."
			::= { hwTrngAbsoluteEntry 3 }


		hwTimerangeAbsoluteEndTime OBJECT-TYPE
			SYNTAX DateAndTime
			MAX-ACCESS read-create
			STATUS current
			DESCRIPTION
				"End point of the timerange.The format defined like 'YYYY-MM-DD,hh:mm:0.0'."
			::= { hwTrngAbsoluteEntry 4 }


		hwTimerangeAbsolueRowStatus OBJECT-TYPE
			SYNTAX RowStatus
			MAX-ACCESS read-create
			STATUS current
			DESCRIPTION
				"The status of this conceptual row. Now only realize CreateAndGo and Destroy and Active."
			::= { hwTrngAbsoluteEntry 5 }


		hwTrngPeriodicTable OBJECT-TYPE
			SYNTAX SEQUENCE OF HwTrngPeriodicEntry
			MAX-ACCESS not-accessible
			STATUS current
			DESCRIPTION
				"Creat periodic time item of the TimeRange"
			::= { hwTRNGMibObjects 3 }


		hwTrngPeriodicEntry OBJECT-TYPE
			SYNTAX HwTrngPeriodicEntry
			MAX-ACCESS not-accessible
			STATUS current
			DESCRIPTION
				"Define the index of hwTrngPeriodicTable"
			INDEX { hwTrngPeriodicNameIndex, hwTrngPeriodicSubIndex }
			::= { hwTrngPeriodicTable 1 }


		HwTrngPeriodicEntry ::=
			SEQUENCE {
				hwTrngPeriodicNameIndex
					Integer32,
				hwTrngPeriodicSubIndex
					Integer32,
				hwTrngPeriodicDayOfWeek
					BITS,
				hwTimerangePeriodicStartTime
					DateAndTime,
				hwTimerangePeriodicEndTime
					DateAndTime,
				hwTimerangePeriodicRowStatus
					RowStatus
			 }

		hwTrngPeriodicNameIndex OBJECT-TYPE
			SYNTAX Integer32 (1..256)
			MAX-ACCESS not-accessible
			STATUS current
			DESCRIPTION
				"TimeRange's index"
			::= { hwTrngPeriodicEntry 1 }


		hwTrngPeriodicSubIndex OBJECT-TYPE
			SYNTAX Integer32 (1..32)
			MAX-ACCESS not-accessible
			STATUS current
			DESCRIPTION
				"SubItem's index"
			::= { hwTrngPeriodicEntry 2 }


		hwTrngPeriodicDayOfWeek OBJECT-TYPE
			SYNTAX BITS {
                              		sunday(0),
                              		monday(1),
                              		tuesday(2),
                              		wednesday(3),
                              		thursday(4),
                              		friday(5),
                              		saturday(6)
                             	     }
			MAX-ACCESS read-create
			STATUS current
			DESCRIPTION
				"The day of week. This is a bit-map of possible conditions.
				The various bit positions are:
				|0		|sunday	            	|
				|1		|monday             	|
				|2		|tuesday            	|
				|3		|wednesday          	|
				|4		|thursday           	|
				|5		|friday             	|
				|6		|saturday           	|
				"
			::= { hwTrngPeriodicEntry 3 }


		hwTimerangePeriodicStartTime OBJECT-TYPE
			SYNTAX DateAndTime
			MAX-ACCESS read-create
			STATUS current
			DESCRIPTION
				"Start point of this timerange,The format defined like 'hh:mm:0,0'."
			::= { hwTrngPeriodicEntry 4 }


		hwTimerangePeriodicEndTime OBJECT-TYPE
			SYNTAX DateAndTime
			MAX-ACCESS read-create
			STATUS current
			DESCRIPTION
				"End point of this timerange. The format definedlike 'hh:mm:0,0'."
			::= { hwTrngPeriodicEntry 5 }


		hwTimerangePeriodicRowStatus OBJECT-TYPE
			SYNTAX RowStatus
			MAX-ACCESS read-create
			STATUS current
			DESCRIPTION
				"The status of this conceptual row, Now only realize CreateAndGo and Destroy and Active."
			::= { hwTrngPeriodicEntry 6 }

		hwTRNGMibConformance OBJECT IDENTIFIER ::= { hwTRNG 3 }


		hwTRNGMibCompliances OBJECT IDENTIFIER ::= { hwTRNGMibConformance 1 }


		hwTRNGMibCompliance MODULE-COMPLIANCE
			STATUS current
			DESCRIPTION
				"The compliance statement for entities which
				implement the Huawei Time-range MIB."
			MODULE -- this module
				MANDATORY-GROUPS { hwTRNGGroup }
				OBJECT hwTrngCreateRowStatus
					SYNTAX INTEGER
					DESCRIPTION
						"Now only realize CreateAndGo and Destroy and Active."
				OBJECT hwTimerangeAbsolueRowStatus
					SYNTAX INTEGER
					DESCRIPTION
						"Now only realize CreateAndGo and Destroy and Active."
				OBJECT hwTimerangePeriodicRowStatus
					SYNTAX INTEGER
					DESCRIPTION
						"Now only realize CreateAndGo and Destroy and Active."
			::= { hwTRNGMibCompliances 1 }


		hwTRNGMibGroups OBJECT IDENTIFIER ::= { hwTRNGMibConformance 2 }


		hwTRNGGroup OBJECT-GROUP
			OBJECTS { hwTrngName, hwTrngValidFlag, hwTrngCreateRowStatus, hwTimerangeAbsoluteStartTime, hwTimerangeAbsoluteEndTime,
				hwTimerangeAbsolueRowStatus, hwTrngPeriodicDayOfWeek, hwTimerangePeriodicStartTime, hwTimerangePeriodicEndTime, hwTimerangePeriodicRowStatus
				 }
			STATUS current
			DESCRIPTION
				"A collection of objects providing mandatory time-range information."
			::= { hwTRNGMibGroups 1 }



	END
