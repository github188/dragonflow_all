-- =========================================================================
-- Copyright (C) 2001,2002 by  HUAWEI TECHNOLOGIES. All rights reserved.
--
-- Description:This file describes various common MIB objects implemented by both
-- Routers and Switches for use by 3Com Network Management applications.
-- Reference:Huawei enterprise MIB
-- =========================================================================
HUAWEI-AR46-DEV-ADM-MIB DEFINITIONS ::= BEGIN

        IMPORTS
            Integer32, OBJECT-TYPE, MODULE-IDENTITY, NOTIFICATION-TYPE
                FROM SNMPv2-SMI
            mlsr
                FROM HUAWEI-3COM-OID-MIB;


        aR46-E200 MODULE-IDENTITY
            LAST-UPDATED "200310221643Z"        -- March 27, 2003 at 16:43 GMT
            ORGANIZATION
                "8060 Team Huawei Tech. "
            CONTACT-INFO
                "liuaki 03198/huawei@huawei."
            DESCRIPTION
                "This MIB is designed and realized by ChenWenjun for 8060 on March 27, 2003. Modified by Liukai on Oct 22, 2003"
            ::= { mlsr 20 }


--
-- Node definitions
--

        hw8060DevObjects OBJECT IDENTIFIER ::= { aR46-E200 1 }

        hw8060FrameTable OBJECT-TYPE
            SYNTAX SEQUENCE OF Hw8060FrameEntry
            MAX-ACCESS not-accessible
            STATUS current
            DESCRIPTION
                "Frame table."
            ::= { hw8060DevObjects 1 }

        hw8060FrameEntry OBJECT-TYPE
            SYNTAX Hw8060FrameEntry
            MAX-ACCESS not-accessible
            STATUS current
            DESCRIPTION
                "Frame table entry."
            INDEX { hw8060FrameIndex }
            ::= { hw8060FrameTable 1 }

        Hw8060FrameEntry ::=
            SEQUENCE {
                hw8060FrameIndex
                    Integer32,
                hw8060FrameType
                    Integer32,
                hw8060FrameDesc
                    OCTET STRING,
                hw8060FrameSlotNumber
                    Integer32,
                hw8060FrameAdminStatus
                    Integer32
             }

        hw8060FrameIndex OBJECT-TYPE
            SYNTAX Integer32 (0..100)
            MAX-ACCESS read-only
            STATUS current
            DESCRIPTION
                "This variable indicates the index of the frame"
            ::= { hw8060FrameEntry 1 }

        hw8060FrameType OBJECT-TYPE
            SYNTAX Integer32
            MAX-ACCESS read-only
            STATUS current
            DESCRIPTION
                "This variable indicates the type of the frame"
            ::= { hw8060FrameEntry 2 }

        hw8060FrameDesc OBJECT-TYPE
            SYNTAX OCTET STRING (SIZE (1..64))
            MAX-ACCESS read-write
            STATUS current
            DESCRIPTION
                "This variable indicates the description of the frame"
            ::= { hw8060FrameEntry 3 }

        hw8060FrameSlotNumber OBJECT-TYPE
            SYNTAX Integer32
            MAX-ACCESS read-only
            STATUS current
            DESCRIPTION
                "This variable indicates the total number of slots in the frame"
            ::= { hw8060FrameEntry 4 }

        hw8060FrameAdminStatus OBJECT-TYPE
            SYNTAX Integer32
            MAX-ACCESS read-only
            STATUS current
            DESCRIPTION
                "This variable indicates the administration status of the frame"
            ::= { hw8060FrameEntry 5 }

        hw8060SlotTable OBJECT-TYPE
            SYNTAX SEQUENCE OF Hw8060SlotEntry
            MAX-ACCESS not-accessible
            STATUS current
            DESCRIPTION
                "Slot table."
            ::= { hw8060DevObjects 2 }

        hw8060SlotEntry OBJECT-TYPE
            SYNTAX Hw8060SlotEntry
            MAX-ACCESS not-accessible
            STATUS current
            DESCRIPTION
                "Slot table entry."
            INDEX { hw8060SlotIndex }
            ::= { hw8060SlotTable 1 }

        Hw8060SlotEntry ::=
            SEQUENCE {
                hw8060SlotIndex
                    Integer32,
                hw8060SlotType
                    INTEGER,
                hw8060SlotDesc
                    OCTET STRING,
                hw8060SlotCpuRatio
                    Integer32,
                hw8060SlotPcbVersion
                    OCTET STRING,
                hw8060SlotSoftwareVersion
                    OCTET STRING,
                hw8060SlotSubslotNumber
                    Integer32,
                hw8060SlotAdminStatus
                    Integer32,
                hw8060SlotOperStatus
                    Integer32
             }

        hw8060SlotIndex OBJECT-TYPE
            SYNTAX Integer32 (0..100)
            MAX-ACCESS read-only
            STATUS current
            DESCRIPTION
                "This variable indicates the index of the current slot"
            ::= { hw8060SlotEntry 1 }

        hw8060SlotType OBJECT-TYPE
            SYNTAX INTEGER
                {
                unavailable(1),
                as(2),
                ss(3),
                bi(4),
                e12(5),
                e14(6),
                fe1(7),
                e1(8),
                fe2(9),
                vi2(11),
                vi4(12),
                vi30(13),
                s1b(14),
                sa2(15),
                as16(16),
                new8as(17),
                lsa(18),
                fxs2(19),
                fxo2(20),
                em2(21),
                fxs4(22),
                fxo4(23),
                em4(24),
                sab(25),
                e1vi(26),
                am12(27),
                am6(28),
                ndec(29),
                newsa2(30),
                aux(31),
                console(32),
                sic-wan(33),
                sic-1fe(34),
                sic-1sa(35),
                sic-3as(36),
                sic-1e1(37),
                sic-1t1(38),
                sic-1bu(39),
                sic-2bu(40),
                sic-1bs(41),
                sic-2bs(42),
                sic-1am(43),
                sic-2am(44),
                sic-1em(45),
                sic-2em(46),
                sic-1fxs(47),
                sic-2fxs(48),
                sic-1fxo(49),
                sic-2fxo(50),
                fcm6(51),
                sa8(52),
                t11(53),
                t12(54),
                t14(55),
                t1vi(56),
                fcm4(57),
                fcm2(58),
                rtb21ce3(59),
                ame6(60),
                ame12(61),
                e11-f(65),
                e12-f(66),
                e14-f(67),
                t11-f(68),
                t12-f(69),
                t14-f(70),
                e11-f-17(71),
                t11-f-17(72),
                rtb21ct3(73),
                atmadsl1(74),
                atmadsl2(75),
                atm155m(76),
                ase8(77),
                ase16(78),
                sae4(79),
                sae2(80),
                atmshdsl1(90),
                atmshdsl2(91),
                atmshdsl4(92),
                atm25m(93),
                atme3(94),
                atmt3(95),
                xdsl-fec(96),
                xdsl-adsl(97),
                xdsl-gshdsl(98),
                xdsl-bri(99),
                xdsl-scc(100),
                ge1(101),
                pos155m(102),
                cpos(103),
                fe1op(104),
                sae8(105),
                atm155m-mm(106),
                atm155m-sm(107),
                atm155m-sml(108),
                fe1op-sfx(109),
                fe1op-mfx(110),
                cpos-t1(111),
                ge1-op(112),
                ge2-op(113),
                ge2(114),
                fix-1wan(115),
                fix-1sae(116),
                cavium(117),
                sic-1Eth(118),
                atm1ADSLI(119),
                atm2ADSLI(120),
                fix-e11(121),
                fix-t11(122),
                e18-75(123),
                e18-120(124),
                t18(125),
                sic-1vifxs(126),
                sic-1vifxo(127),
                sic-2vifxs(128),
                sic-2vifxo(129),
                xdsl-fec-new(130),
                xdsl-sa(131),
                bs4(132),
                ima-8e175(133),
                ima-8e1120(134),
                ima-4e175(135),
                ima-4e1120(136),
                ima-8t1(137),
                ima-4t1(138),
                sic-1t1f(139),
                sic-1e1f(140),
                --  the enum values from 141 to 150 are reserved.
                atm1shdsl4wire(151),
                atmIma4shdsl(152),
                ls4(153),
                ls8(154),
                ls16(155),
                sic-adls2plus-isdn(156),
                sic-adls2plus-pots(157),
                ft3(158),
                ce32(159),
                bsv2(160),
                bsv4(161),
                rpu(162),
                erpu(163),
                fe18-75(220),
                fe18-120(221),
                ft18(222),
                cf-card(223),
                bsv2-v2(224),
                e1vi1-v2(225),
                e1vi2(226),
                t1vi1-v2(227),
                t1vi2(228),
                osm(229),
                sd707(230),
                dm-epri(231),
                dm-tpri(232),
                erpu-h(233)
                }
            MAX-ACCESS read-only
            STATUS current
            DESCRIPTION
                "This variable indicates the type of the current slot"
            ::= { hw8060SlotEntry 2 }

        hw8060SlotDesc OBJECT-TYPE
            SYNTAX OCTET STRING (SIZE (0..64))
            MAX-ACCESS read-write
            STATUS current
            DESCRIPTION
                "This variable indicates the description of the current slot;
                Max length is 64,0 indicates no description."
            ::= { hw8060SlotEntry 3 }

        hw8060SlotCpuRatio OBJECT-TYPE
            SYNTAX Integer32
            MAX-ACCESS read-only
            STATUS current
            DESCRIPTION
                "This variable indicates the ratio of CPU the current slot occupied"
            ::= { hw8060SlotEntry 4 }

        hw8060SlotPcbVersion OBJECT-TYPE
            SYNTAX OCTET STRING
            MAX-ACCESS read-only
            STATUS current
            DESCRIPTION
                "This variable indicates the PCB version of the current slot"
            ::= { hw8060SlotEntry 5 }

        hw8060SlotSoftwareVersion OBJECT-TYPE
            SYNTAX OCTET STRING
            MAX-ACCESS read-only
            STATUS current
            DESCRIPTION
                "This variable indicates the software version of the current slot"
            ::= { hw8060SlotEntry 6 }

        hw8060SlotSubslotNumber OBJECT-TYPE
            SYNTAX Integer32
            MAX-ACCESS read-only
            STATUS current
            DESCRIPTION
                "This variable indicates the total number of subslots in the current slot"
            ::= { hw8060SlotEntry 7 }

        hw8060SlotAdminStatus OBJECT-TYPE
            SYNTAX Integer32
            MAX-ACCESS read-only
            STATUS current
            DESCRIPTION
                "This variable indicates the administration status of the current slot"
            ::= { hw8060SlotEntry 8 }

        hw8060SlotOperStatus OBJECT-TYPE
            SYNTAX Integer32
            MAX-ACCESS read-only
            STATUS current
            DESCRIPTION
                "This variable indicates the operatrion status of the current slot"
            ::= { hw8060SlotEntry 9 }

        hw8060SubslotTable OBJECT-TYPE
            SYNTAX SEQUENCE OF Hw8060SubslotEntry
            MAX-ACCESS not-accessible
            STATUS current
            DESCRIPTION
                "Subslot table."
            ::= { hw8060DevObjects 3 }

        hw8060SubslotEntry OBJECT-TYPE
            SYNTAX Hw8060SubslotEntry
            MAX-ACCESS not-accessible
            STATUS current
            DESCRIPTION
                "Subslot table entry."
            INDEX { hw8060SlotIndex, hw8060SubslotIndex }
            ::= { hw8060SubslotTable 1 }

        Hw8060SubslotEntry ::=
            SEQUENCE {
                hw8060SubslotIndex
                    Integer32,
                hw8060SubslotType
                    Integer32,
                hw8060SubslotPortNum
                    Integer32,
                hw8060SubslotAdminStatus
                    Integer32
             }

        hw8060SubslotIndex OBJECT-TYPE
            SYNTAX Integer32 (0..100)
            MAX-ACCESS read-only
            STATUS current
            DESCRIPTION
                "This variable indicates the index of the current subslot.
                Max value of index is 100,0 indicates none."
            ::= { hw8060SubslotEntry 1 }

        hw8060SubslotType OBJECT-TYPE
            SYNTAX Integer32
            MAX-ACCESS read-only
            STATUS current
            DESCRIPTION
                "This variable indicates the type of the current subslot"
            ::= { hw8060SubslotEntry 2 }

        hw8060SubslotPortNum OBJECT-TYPE
            SYNTAX Integer32
            MAX-ACCESS read-only
            STATUS current
            DESCRIPTION
                "This variable indicates the total number of ports in the current subslot"
            ::= { hw8060SubslotEntry 3 }

        hw8060SubslotAdminStatus OBJECT-TYPE
            SYNTAX Integer32
            MAX-ACCESS read-only
            STATUS current
            DESCRIPTION
                "This variable indicates the administration status of the current subslot"
            ::= { hw8060SubslotEntry 4 }

        hw8060PortTable OBJECT-TYPE
            SYNTAX SEQUENCE OF Hw8060PortEntry
            MAX-ACCESS not-accessible
            STATUS current
            DESCRIPTION
                "Port table."
            ::= { hw8060DevObjects 4 }

        hw8060PortEntry OBJECT-TYPE
            SYNTAX Hw8060PortEntry
            MAX-ACCESS not-accessible
            STATUS current
            DESCRIPTION
                "Port table entry."
            INDEX { hw8060SlotIndex, hw8060SubslotIndex, hw8060PortIndex }
            ::= { hw8060PortTable 1 }

        Hw8060PortEntry ::=
            SEQUENCE {
                hw8060PortIndex
                    Integer32,
                hw8060PortType
                    Integer32,
                hw8060PortDesc
                    OCTET STRING,
                hw8060PortSpeed
                    Integer32,
                hw8060PortAdminStatus
                    Integer32,
                hw8060PortOperateStatus
                    Integer32
             }

        hw8060PortIndex OBJECT-TYPE
            SYNTAX Integer32 (0..100)
            MAX-ACCESS read-only
            STATUS current
            DESCRIPTION
                "This variable indicates the index of the current port"
            ::= { hw8060PortEntry 1 }

        hw8060PortType OBJECT-TYPE
            SYNTAX Integer32
            MAX-ACCESS read-only
            STATUS current
            DESCRIPTION
                "This variable indicates the type of the current subslot"
            ::= { hw8060PortEntry 2 }

        hw8060PortDesc OBJECT-TYPE
            SYNTAX OCTET STRING (SIZE (1..64))
            MAX-ACCESS read-only
            STATUS current
            DESCRIPTION
                "This variable indicates the description of the current subslot"
            ::= { hw8060PortEntry 3 }

        hw8060PortSpeed OBJECT-TYPE
            SYNTAX Integer32
            MAX-ACCESS read-only
            STATUS current
            DESCRIPTION
                "This variable indicates the speed in bps of the current subslot"
            ::= { hw8060PortEntry 4 }

        hw8060PortAdminStatus OBJECT-TYPE
            SYNTAX Integer32
            MAX-ACCESS read-only
            STATUS current
            DESCRIPTION
                "This variable indicates the administration status of the current subslot"
            ::= { hw8060PortEntry 5 }

        hw8060PortOperateStatus OBJECT-TYPE
            SYNTAX Integer32
            MAX-ACCESS read-only
            STATUS current
            DESCRIPTION
                "This variable indicates the operation status of the current subslot"
            ::= { hw8060PortEntry 6 }

        dev8060MPowerStatusTable OBJECT-TYPE
            SYNTAX SEQUENCE OF Dev8060MPowerStatusEntry
            MAX-ACCESS not-accessible
            STATUS current
            DESCRIPTION          "the info about powers"
            ::= { hw8060DevObjects 5 }

        dev8060MPowerStatusEntry OBJECT-TYPE
            SYNTAX Dev8060MPowerStatusEntry
            MAX-ACCESS not-accessible
            STATUS current
            DESCRIPTION
                "the info about powers."
            INDEX { dev8060MPowerNum }
            ::= { dev8060MPowerStatusTable 1 }

        Dev8060MPowerStatusEntry ::=
            SEQUENCE {
                dev8060MPowerNum
                    Integer32,
                dev8060MPowerStatus
                    INTEGER
             }

        dev8060MPowerNum OBJECT-TYPE
            SYNTAX Integer32 (0..10)
            MAX-ACCESS read-only
            STATUS current
            DESCRIPTION
                "This variable indicates the sequence number of the current power.
                Max number is 10,0 indicates nonsupport this node."
            ::= { dev8060MPowerStatusEntry 1 }

        dev8060MPowerStatus OBJECT-TYPE
            SYNTAX INTEGER {
                    ok(1),
                    fail(2)
            }
            MAX-ACCESS read-only
            STATUS current
            DESCRIPTION
                "This variable indicates the working status of the current power.
                ok(1)          the power state is normal.
                fail(2)        the power state is abnormal.
                "
            ::= { dev8060MPowerStatusEntry 2 }

        dev8060MFanStatusTable OBJECT-TYPE
            SYNTAX SEQUENCE OF Dev8060MFanStatusEntry
            MAX-ACCESS not-accessible
            STATUS current
            DESCRIPTION          "the info about Fans"
            ::= { hw8060DevObjects 6 }

        dev8060MFanStatusEntry OBJECT-TYPE
            SYNTAX Dev8060MFanStatusEntry
            MAX-ACCESS not-accessible
            STATUS current
            DESCRIPTION
                "the info about Fans."
            INDEX { dev8060MFanNum }
            ::= { dev8060MFanStatusTable 1 }

        Dev8060MFanStatusEntry ::=
            SEQUENCE {
                dev8060MFanNum
                    Integer32,
                dev8060MFanStatus
                    INTEGER
             }

        dev8060MFanNum OBJECT-TYPE
            SYNTAX Integer32 (0..10)
            MAX-ACCESS read-only
            STATUS current
            DESCRIPTION
                "This variable indicates the sequence number of the current fan.
                Max value is 10,0 indicates no fan."
            ::= { dev8060MFanStatusEntry 1 }

        dev8060MFanStatus OBJECT-TYPE
            SYNTAX INTEGER {
                ok(1),
                fail(2)
            }
            MAX-ACCESS read-only
            STATUS current
            DESCRIPTION
                "This variable indicates the working status of the current fan.
                    ok(1)          the fan state is normal.
                    fail(2)        the fan state is abnormal.
                "
            ::= { dev8060MFanStatusEntry 2 }

        dev8060MGlobalTable OBJECT IDENTIFIER ::= { hw8060DevObjects 7 }

        hw8060DevMRpuTemperature OBJECT-TYPE
            SYNTAX Integer32
            MAX-ACCESS read-only
            STATUS current
            DESCRIPTION
                   "This variable indicates the temperature of RPU."
            ::= { dev8060MGlobalTable 1 }

        hw8060DevMTemperatureMax OBJECT-TYPE
            SYNTAX Integer32
            MAX-ACCESS read-write
            STATUS current
            DESCRIPTION
                "This variable indicates the maximum temperature set by user"
            ::= { dev8060MGlobalTable 2 }

        hw8060DevMTemperatureMin OBJECT-TYPE
            SYNTAX Integer32
            MAX-ACCESS read-write
            STATUS current
            DESCRIPTION
                "This variable indicates the minimum temperature set by user"
            ::= { dev8060MGlobalTable 3 }

        hw8060SysVersion OBJECT-TYPE
            SYNTAX OCTET STRING
            MAX-ACCESS read-only
            STATUS current
            DESCRIPTION
                "This variable indicates the system version ( big version )"
            ::= { dev8060MGlobalTable 4 }

        hw8060SysTime OBJECT-TYPE
            SYNTAX Integer32
            MAX-ACCESS read-only
            STATUS current
            DESCRIPTION
                "This variable indicates the system time"
            ::= { dev8060MGlobalTable 5 }

        hw8060DevMVentTemperature OBJECT-TYPE
            SYNTAX Integer32
            MAX-ACCESS read-only
            STATUS current
            DESCRIPTION          " "
            ::= { dev8060MGlobalTable 6 }

        hw8060DevNotifications OBJECT IDENTIFIER ::= { aR46-E200 2 }

        hwRpuTempTooHigh NOTIFICATION-TYPE
            STATUS current
            DESCRIPTION          "The notification indicates that the temperature of RPU is too high"
            ::= { hw8060DevNotifications 1 }

        hwRpuTempOK NOTIFICATION-TYPE
            STATUS current
            DESCRIPTION
                "The notification indicates that The temperature of RPU is normal"
            ::= { hw8060DevNotifications 2 }

        hwNpTempTooHigh NOTIFICATION-TYPE
            STATUS current
            DESCRIPTION
                "The notification indicates that The temperature of NP exceeds the maximum"
            ::= { hw8060DevNotifications 3 }

        hwNpTempOK NOTIFICATION-TYPE
            STATUS current
            DESCRIPTION
                "The notification indicates that The temperature of NP is normal"
            ::= { hw8060DevNotifications 4 }

        hwRpuTempTooLow NOTIFICATION-TYPE
            STATUS current
            DESCRIPTION
                "The notification indicates that The temperature of RPU is too low"
            ::= { hw8060DevNotifications 5 }

        hwNpTempTooLow NOTIFICATION-TYPE
            STATUS current
            DESCRIPTION
                "The notification indicates that The temperature of NP is too low"
            ::= { hw8060DevNotifications 6 }

        hwVentTempTooHigh NOTIFICATION-TYPE
            STATUS current
            DESCRIPTION
                "The notification indicates that The temperature of VENT exceeds the maximum"
            ::= { hw8060DevNotifications 7 }

        hwVentTempOK NOTIFICATION-TYPE
            STATUS current
            DESCRIPTION
                "The notification indicates that The temperature of VENT is normal"
            ::= { hw8060DevNotifications 9 }

        hwRpuReset NOTIFICATION-TYPE
            STATUS current
            DESCRIPTION "The notification indicates that the RPU reset"
            ::= { hw8060DevNotifications 10 }

        hwRpuResetOK NOTIFICATION-TYPE
            STATUS current
            DESCRIPTION
                "The notification indicates that RPU reset successfully"
            ::= { hw8060DevNotifications 11 }

        hwNpReset NOTIFICATION-TYPE
            STATUS current
            DESCRIPTION
                "The notification indicates that NP reset"
            ::= { hw8060DevNotifications 12 }

        hwNpResetOK NOTIFICATION-TYPE
            STATUS current
            DESCRIPTION
                "The notification indicates that NP reset successfully"
            ::= { hw8060DevNotifications 13 }

        hwSlotReset NOTIFICATION-TYPE
            OBJECTS { hw8060SlotIndex }
            STATUS current
            DESCRIPTION
                "The notification indicates that Slot reset"
            ::= { hw8060DevNotifications 14 }

        hwSlotResetOK NOTIFICATION-TYPE
            OBJECTS { hw8060SlotIndex }
            STATUS current
            DESCRIPTION
                "The notification indicates that Slot reset successfully"
            ::= { hw8060DevNotifications 15 }

        hwPciAlarm NOTIFICATION-TYPE
            STATUS current
            DESCRIPTION
                "The notification indicates that PCI alarm occurred"
            ::= { hw8060DevNotifications 16 }

        hwPciNormal NOTIFICATION-TYPE
            STATUS current
            DESCRIPTION
                "The notification indicates that PCI is normal"
            ::= { hw8060DevNotifications 17 }

        hwRpuIntReportErr NOTIFICATION-TYPE
            STATUS current
            DESCRIPTION
                "The notification indicates that RPU report wrong interrupts too frequently"
            ::= { hw8060DevNotifications 18 }

        hwNpIntReportErr NOTIFICATION-TYPE
            STATUS current
            DESCRIPTION
                "The notification indicates that NP report wrong interrupts too frequently"
            ::= { hw8060DevNotifications 19 }

        hwSlotIntReportErr NOTIFICATION-TYPE
            OBJECTS { hw8060SubslotIndex }
            STATUS current
            DESCRIPTION
                "The notification indicates that Slot report wrong interrupts too frequently"
            ::= { hw8060DevNotifications 20 }

        hwWriteFlashErr NOTIFICATION-TYPE
            STATUS current
            DESCRIPTION
                "The notification indicates that Write FLASH failed"
            ::= { hw8060DevNotifications 21 }

        hwPowerUnitFail NOTIFICATION-TYPE
            OBJECTS { dev8060MPowerNum }
            STATUS current
            DESCRIPTION
                "The notification indicates that Power failed"
            ::= { hw8060DevNotifications 22 }

        hwPowerUnitNormal NOTIFICATION-TYPE
            OBJECTS { dev8060MPowerNum }
            STATUS current
            DESCRIPTION
                "The notification indicates that Power is normal"
            ::= { hw8060DevNotifications 23 }

        hwFanUnitFail NOTIFICATION-TYPE
            OBJECTS { dev8060MFanNum }
            STATUS current
            DESCRIPTION
                "The notification indicates that Fan failed"
            ::= { hw8060DevNotifications 24 }

        hwFanUnitNormal NOTIFICATION-TYPE
            OBJECTS { dev8060MFanNum }
            STATUS current
            DESCRIPTION
                "The notification indicates that Fan is normal"
            ::= { hw8060DevNotifications 25 }

        hwFtpLoadFail NOTIFICATION-TYPE
            STATUS current
            DESCRIPTION
                "The notification indicates that FTP failed"
            ::= { hw8060DevNotifications 26 }

        hwTftpLoadFail NOTIFICATION-TYPE
            STATUS current
            DESCRIPTION
                "The notification indicates that TFTP failed"
            ::= { hw8060DevNotifications 27 }

        hwXmodemLoadFail NOTIFICATION-TYPE
            STATUS current
            DESCRIPTION
                "The notification indicates that XMODEM failed"
            ::= { hw8060DevNotifications 28 }

        hwNpConfPathErr NOTIFICATION-TYPE
            STATUS current
            DESCRIPTION
                "The notification indicates that NP configuration path is abnormal"
            ::= { hw8060DevNotifications 29 }

        hwHSCardConfPathErr NOTIFICATION-TYPE
            OBJECTS { hw8060SubslotIndex }
            STATUS current
            DESCRIPTION
                "The notification indicates that High speed card configuration path is abnormal"
            ::= { hw8060DevNotifications 30 }

        hwLSCardJtagErr NOTIFICATION-TYPE
            OBJECTS { hw8060SubslotIndex }
            STATUS current
            DESCRIPTION
                "The notification indicates that Low speed card JTAG path is abnormal"
            ::= { hw8060DevNotifications 31 }

        hwHSCardJtagErr NOTIFICATION-TYPE
            OBJECTS { hw8060SubslotIndex }
            STATUS current
            DESCRIPTION
                "The notification indicates that High speed card JTAG path is abnormal"
            ::= { hw8060DevNotifications 32 }

        hwNpuJtagErr NOTIFICATION-TYPE
            STATUS current
            DESCRIPTION
                "The notification indicates that NP JTAG path is abnormal"
            ::= { hw8060DevNotifications 33 }

        hwNpRpuDmuErr NOTIFICATION-TYPE
            STATUS current
            DESCRIPTION
                "The notification indicates that DMU path between NP and RPU is abnormal"
            ::= { hw8060DevNotifications 34 }

        hwLSCardHealthyErr NOTIFICATION-TYPE
            OBJECTS { hw8060SubslotIndex }
            STATUS current
            DESCRIPTION
                "The notification indicates that Low speed card healthy signal is abnormal"
            ::= { hw8060DevNotifications 35 }

        hwHSCardHealthyErr NOTIFICATION-TYPE
            OBJECTS { hw8060SubslotIndex }
            STATUS current
            DESCRIPTION
                "The notification indicates that High speed card healthy signal is abnormal"
            ::= { hw8060DevNotifications 36 }

        hwCardPciHealthyErr NOTIFICATION-TYPE
            OBJECTS { hw8060SubslotIndex }
            STATUS current
            DESCRIPTION
                "The notification indicates that Slot PCI_HEALTHY signal is abnormal"
            ::= { hw8060DevNotifications 37 }

        hwHSCardPowerErr NOTIFICATION-TYPE
            OBJECTS { hw8060SubslotIndex }
            STATUS current
            DESCRIPTION
                "The notification indicates that Slot HEALTHY signal is invalid"
            ::= { hw8060DevNotifications 38 }

        hwVentTempTooLow NOTIFICATION-TYPE
            STATUS current
            DESCRIPTION
                "The notification indicates that the temperature of VENT is too low"
            ::= { hw8060DevNotifications 39 }

        hw8060DevConformance OBJECT IDENTIFIER ::= { aR46-E200 3 }


    END
