S-guard-MIB DEFINITIONS ::= BEGIN

-- *VERSION* 1.0
	
	IMPORTS
		OBJECT-TYPE
			FROM RFC-1212
		TRAP-TYPE
			FROM RFC-1215
		enterprises
			FROM RFC1155-SMI
                DisplayString
                        FROM RFC1213-MIB;

	schroffGmbH OBJECT IDENTIFIER ::= {enterprises 2012}

	sguard OBJECT IDENTIFIER ::= {schroffGmbH 30}

-- -------------------------------------------------------------------
-- TABLE of Sensors --
        sensTable OBJECT-TYPE
              SYNTAX  SEQUENCE OF SensEntry
              ACCESS  not-accessible
              STATUS  mandatory
              DESCRIPTION
                      "A list of all sensors connected. Each Sensor has
		      a unique ID containing sensortype and serial number."
              ::= { sguard 1 }

          sensEntry OBJECT-TYPE
              SYNTAX  SensEntry
              ACCESS  not-accessible
              STATUS  mandatory
              DESCRIPTION
                      "Entry of one sensor"
              INDEX   { id }
              ::= { sensTable 1 }

          SensEntry ::=
              SEQUENCE {
                  id DisplayString,
		  value DisplayString,
		  unit	DisplayString,
		  valueint INTEGER
		  }
		  
          id OBJECT-TYPE
              SYNTAX  DisplayString
              ACCESS  read-only
              STATUS  mandatory


              DESCRIPTION
                      "A unique value containing sensortype and serial number."
              ::= { sensEntry 1 }

	  value OBJECT-TYPE
              SYNTAX  DisplayString
              ACCESS  read-only
              STATUS  mandatory


              DESCRIPTION
                      "The value of the sensor as String."
              ::= { sensEntry 2 }

	  unit OBJECT-TYPE
              SYNTAX  DisplayString
              ACCESS  read-only
              STATUS  mandatory


              DESCRIPTION
                      "The unit of the sensor."
              ::= { sensEntry 3 }

	  valueint OBJECT-TYPE
              SYNTAX  INTEGER
              ACCESS  read-only
              STATUS  mandatory


              DESCRIPTION
                      "The value of the sensor times 1000 as integer"
              ::= { sensEntry 4 }

	      
          numSens OBJECT-TYPE
              SYNTAX  INTEGER
              ACCESS  read-only
              STATUS  mandatory


              DESCRIPTION
                      "Number of sensors connected"
              ::= { sguard 2 }


-- -------------------------------------------------------------------
-- Groups in sguard
        sensorGroup1 OBJECT IDENTIFIER ::= { sguard 3 }

-- Groups.Sensors in sguard
          s1     OBJECT IDENTIFIER ::= { sensorGroup1 1 }
          s2     OBJECT IDENTIFIER ::= { sensorGroup1 2 }
          s3     OBJECT IDENTIFIER ::= { sensorGroup1 3 }
          s4     OBJECT IDENTIFIER ::= { sensorGroup1 4 }
          s5     OBJECT IDENTIFIER ::= { sensorGroup1 5 }
          s6     OBJECT IDENTIFIER ::= { sensorGroup1 6 }
          s7     OBJECT IDENTIFIER ::= { sensorGroup1 7 }
          s8     OBJECT IDENTIFIER ::= { sensorGroup1 8 }
          s9     OBJECT IDENTIFIER ::= { sensorGroup1 9 }
          s10    OBJECT IDENTIFIER ::= { sensorGroup1 10 }

          s11    OBJECT IDENTIFIER ::= { sensorGroup1 11 }
          s12    OBJECT IDENTIFIER ::= { sensorGroup1 12 }
          s13    OBJECT IDENTIFIER ::= { sensorGroup1 13 }
          s14    OBJECT IDENTIFIER ::= { sensorGroup1 14 }
          s15    OBJECT IDENTIFIER ::= { sensorGroup1 15 }
          s16    OBJECT IDENTIFIER ::= { sensorGroup1 16 }
          s17    OBJECT IDENTIFIER ::= { sensorGroup1 17 }
          s18    OBJECT IDENTIFIER ::= { sensorGroup1 18 }
          s19    OBJECT IDENTIFIER ::= { sensorGroup1 19 }
          s20    OBJECT IDENTIFIER ::= { sensorGroup1 20 }

          s21    OBJECT IDENTIFIER ::= { sensorGroup1 21 }
          s22    OBJECT IDENTIFIER ::= { sensorGroup1 22 }
          s23    OBJECT IDENTIFIER ::= { sensorGroup1 23 }
          s24    OBJECT IDENTIFIER ::= { sensorGroup1 24 }
          s25    OBJECT IDENTIFIER ::= { sensorGroup1 25 }
          s26    OBJECT IDENTIFIER ::= { sensorGroup1 26 }
          s27    OBJECT IDENTIFIER ::= { sensorGroup1 27 }
          s28    OBJECT IDENTIFIER ::= { sensorGroup1 28 }
          s29    OBJECT IDENTIFIER ::= { sensorGroup1 29 }
          s30    OBJECT IDENTIFIER ::= { sensorGroup1 30 }

          s31    OBJECT IDENTIFIER ::= { sensorGroup1 31 }
          s32    OBJECT IDENTIFIER ::= { sensorGroup1 32 }
          s33    OBJECT IDENTIFIER ::= { sensorGroup1 33 }
          s34    OBJECT IDENTIFIER ::= { sensorGroup1 34 }
          s35    OBJECT IDENTIFIER ::= { sensorGroup1 35 }
          s36    OBJECT IDENTIFIER ::= { sensorGroup1 36 }
          s37    OBJECT IDENTIFIER ::= { sensorGroup1 37 }
          s38    OBJECT IDENTIFIER ::= { sensorGroup1 38 }
          s39    OBJECT IDENTIFIER ::= { sensorGroup1 39 }
          s40    OBJECT IDENTIFIER ::= { sensorGroup1 40 }

          s41    OBJECT IDENTIFIER ::= { sensorGroup1 41 }
          s42    OBJECT IDENTIFIER ::= { sensorGroup1 42 }
          s43    OBJECT IDENTIFIER ::= { sensorGroup1 43 }
          s44    OBJECT IDENTIFIER ::= { sensorGroup1 44 }
          s45    OBJECT IDENTIFIER ::= { sensorGroup1 45 }
          s46    OBJECT IDENTIFIER ::= { sensorGroup1 46 }
          s47    OBJECT IDENTIFIER ::= { sensorGroup1 47 }
          s48    OBJECT IDENTIFIER ::= { sensorGroup1 48 }
          s49    OBJECT IDENTIFIER ::= { sensorGroup1 49 }
          s50    OBJECT IDENTIFIER ::= { sensorGroup1 50 }

          s51    OBJECT IDENTIFIER ::= { sensorGroup1 51 }
          s52    OBJECT IDENTIFIER ::= { sensorGroup1 52 }
          s53    OBJECT IDENTIFIER ::= { sensorGroup1 53 }
          s54    OBJECT IDENTIFIER ::= { sensorGroup1 54 }
          s55    OBJECT IDENTIFIER ::= { sensorGroup1 55 }
          s56    OBJECT IDENTIFIER ::= { sensorGroup1 56 }
          s57    OBJECT IDENTIFIER ::= { sensorGroup1 57 }
          s58    OBJECT IDENTIFIER ::= { sensorGroup1 58 }
          s59    OBJECT IDENTIFIER ::= { sensorGroup1 59 }
          s60    OBJECT IDENTIFIER ::= { sensorGroup1 60 }

          s61    OBJECT IDENTIFIER ::= { sensorGroup1 61 }
          s62    OBJECT IDENTIFIER ::= { sensorGroup1 62 }
          s63    OBJECT IDENTIFIER ::= { sensorGroup1 63 }
          s64    OBJECT IDENTIFIER ::= { sensorGroup1 64 }
          s65    OBJECT IDENTIFIER ::= { sensorGroup1 65 }
          s66    OBJECT IDENTIFIER ::= { sensorGroup1 66 }
          s67    OBJECT IDENTIFIER ::= { sensorGroup1 67 }
          s68    OBJECT IDENTIFIER ::= { sensorGroup1 68 }
          s69    OBJECT IDENTIFIER ::= { sensorGroup1 69 }
          s70    OBJECT IDENTIFIER ::= { sensorGroup1 70 }

          s71    OBJECT IDENTIFIER ::= { sensorGroup1 71 }
          s72    OBJECT IDENTIFIER ::= { sensorGroup1 72 }
          s73    OBJECT IDENTIFIER ::= { sensorGroup1 73 }
          s74    OBJECT IDENTIFIER ::= { sensorGroup1 74 }
          s75    OBJECT IDENTIFIER ::= { sensorGroup1 75 }
          s76    OBJECT IDENTIFIER ::= { sensorGroup1 76 }
          s77    OBJECT IDENTIFIER ::= { sensorGroup1 77 }
          s78    OBJECT IDENTIFIER ::= { sensorGroup1 78 }
          s79    OBJECT IDENTIFIER ::= { sensorGroup1 79 }
          s80    OBJECT IDENTIFIER ::= { sensorGroup1 80 }

          s81    OBJECT IDENTIFIER ::= { sensorGroup1 81 }
          s82    OBJECT IDENTIFIER ::= { sensorGroup1 82 }
          s83    OBJECT IDENTIFIER ::= { sensorGroup1 83 }
          s84    OBJECT IDENTIFIER ::= { sensorGroup1 84 }
          s85    OBJECT IDENTIFIER ::= { sensorGroup1 85 }
          s86    OBJECT IDENTIFIER ::= { sensorGroup1 86 }
          s87    OBJECT IDENTIFIER ::= { sensorGroup1 87 }
          s88    OBJECT IDENTIFIER ::= { sensorGroup1 88 }
          s89    OBJECT IDENTIFIER ::= { sensorGroup1 89 }
          s90    OBJECT IDENTIFIER ::= { sensorGroup1 90 }

          s91    OBJECT IDENTIFIER ::= { sensorGroup1 91 }
          s92    OBJECT IDENTIFIER ::= { sensorGroup1 92 }
          s93    OBJECT IDENTIFIER ::= { sensorGroup1 93 }
          s94    OBJECT IDENTIFIER ::= { sensorGroup1 94 }
          s95    OBJECT IDENTIFIER ::= { sensorGroup1 95 }
          s96    OBJECT IDENTIFIER ::= { sensorGroup1 96 }
          s97    OBJECT IDENTIFIER ::= { sensorGroup1 97 }
          s98    OBJECT IDENTIFIER ::= { sensorGroup1 98 }
          s99    OBJECT IDENTIFIER ::= { sensorGroup1 99 }
          s100   OBJECT IDENTIFIER ::= { sensorGroup1 100 }


-- Groups.Sensors.Defs in sguard

  -- 1-10
	-- sensor1:
            s1id OBJECT-TYPE
              SYNTAX  DisplayString
              ACCESS  read-only
              STATUS  mandatory
              DESCRIPTION
                      "A unique value containing sensortype and serial number."
              ::= { s1 1 }

	    s1value OBJECT-TYPE
              SYNTAX  DisplayString
              ACCESS  read-only
              STATUS  mandatory
              DESCRIPTION
                      "The value of the sensor as String."
              ::= { s1 2 }

	    s1unit OBJECT-TYPE
              SYNTAX  DisplayString
              ACCESS  read-only
              STATUS  mandatory
              DESCRIPTION
                      "The unit of the sensor."
              ::= { s1 3 }

	    s1valueInt OBJECT-TYPE
              SYNTAX  INTEGER
              ACCESS  read-write
              STATUS  mandatory
              DESCRIPTION
                      "The value of the sensor times 1000 as integer"
              ::= { s1 4 }

	    s1name OBJECT-TYPE
              SYNTAX  DisplayString
              ACCESS  read-only
              STATUS  mandatory
              DESCRIPTION
                      "The name of the sensor as String. 
		       This name is set by the user in the SNMP Config Table."
              ::= { s1 5 }

	    s1alarmInt OBJECT-TYPE
              SYNTAX  INTEGER
              ACCESS  read-only
              STATUS  mandatory
              DESCRIPTION
                      "The Sensor Alarm Status range 1..5 as integer"
              ::= { s1 6 }

	    s1LoLimitAlarmInt OBJECT-TYPE
              SYNTAX  INTEGER
              ACCESS  read-only
              STATUS  mandatory
              DESCRIPTION
                      "The lower limit alarm value of the sensor times 1000 as integer"
              ::= { s1 7 }

	    s1LoLimitWarnInt OBJECT-TYPE
              SYNTAX  INTEGER
              ACCESS  read-only
              STATUS  mandatory
              DESCRIPTION
                      "The lower limit warning value of the sensor times 1000 as integer"
              ::= { s1 8 }

	    s1HiLimitWarnInt OBJECT-TYPE
              SYNTAX  INTEGER
              ACCESS  read-only
              STATUS  mandatory
              DESCRIPTION
                      "The upper limit warning value of the sensor times 1000 as integer"
              ::= { s1 9 }

	    s1HiLimitAlarmInt OBJECT-TYPE
              SYNTAX  INTEGER
              ACCESS  read-only
              STATUS  mandatory
              DESCRIPTION
                      "The upper limit alarm value of the sensor times 1000 as integer"
              ::= { s1 10 }

	    s1HysterInt OBJECT-TYPE
              SYNTAX  INTEGER
              ACCESS  read-only
              STATUS  mandatory
              DESCRIPTION
                      "The hysteresis value of the sensor times 1000 as integer"
              ::= { s1 11 }


	-- sensor2:
            s2id OBJECT-TYPE
              SYNTAX  DisplayString
              ACCESS  read-only
              STATUS  mandatory
              DESCRIPTION
                      "A unique value containing sensortype and serial number."
              ::= { s2 1 }

	    s2value OBJECT-TYPE
              SYNTAX  DisplayString
              ACCESS  read-only
              STATUS  mandatory
              DESCRIPTION
                      "The value of the sensor as String."
              ::= { s2 2 }

	    s2unit OBJECT-TYPE
              SYNTAX  DisplayString
              ACCESS  read-only
              STATUS  mandatory
              DESCRIPTION
                      "The unit of the sensor."
              ::= { s2 3 }

	    s2valueInt OBJECT-TYPE
              SYNTAX  INTEGER
              ACCESS  read-write
              STATUS  mandatory
              DESCRIPTION
                      "The value of the sensor times 1000 as integer"
              ::= { s2 4 }

	    s2name OBJECT-TYPE
              SYNTAX  DisplayString
              ACCESS  read-only
              STATUS  mandatory
              DESCRIPTION
                      "The name of the sensor as String. 
		       This name is set by the user in the SNMP Config Table."
              ::= { s2 5 }

	    s2alarmInt OBJECT-TYPE
              SYNTAX  INTEGER
              ACCESS  read-only
              STATUS  mandatory
              DESCRIPTION
                      "The Sensor Alarm Status range 1..5 as integer"
              ::= { s2 6 }

	    s2LoLimitAlarmInt OBJECT-TYPE
              SYNTAX  INTEGER
              ACCESS  read-only
              STATUS  mandatory
              DESCRIPTION
                      "The lower limit alarm value of the sensor times 1000 as integer"
              ::= { s2 7 }

	    s2LoLimitWarnInt OBJECT-TYPE
              SYNTAX  INTEGER
              ACCESS  read-only
              STATUS  mandatory
              DESCRIPTION
                      "The lower limit warning value of the sensor times 1000 as integer"
              ::= { s2 8 }

	    s2HiLimitWarnInt OBJECT-TYPE
              SYNTAX  INTEGER
              ACCESS  read-only
              STATUS  mandatory
              DESCRIPTION
                      "The upper limit warning value of the sensor times 1000 as integer"
              ::= { s2 9 }

	    s2HiLimitAlarmInt OBJECT-TYPE
              SYNTAX  INTEGER
              ACCESS  read-only
              STATUS  mandatory
              DESCRIPTION
                      "The upper limit alarm value of the sensor times 1000 as integer"
              ::= { s2 10 }

	    s2HysterInt OBJECT-TYPE
              SYNTAX  INTEGER
              ACCESS  read-only
              STATUS  mandatory
              DESCRIPTION
                      "The hysteresis value of the sensor times 1000 as integer"
              ::= { s2 11 }


	-- sensor3:
            s3id OBJECT-TYPE
              SYNTAX  DisplayString
              ACCESS  read-only
              STATUS  mandatory
              DESCRIPTION
                      "A unique value containing sensortype and serial number."
              ::= { s3 1 }

	    s3value OBJECT-TYPE
              SYNTAX  DisplayString
              ACCESS  read-only
              STATUS  mandatory
              DESCRIPTION
                      "The value of the sensor as String."
              ::= { s3 2 }

	    s3unit OBJECT-TYPE
              SYNTAX  DisplayString
              ACCESS  read-only
              STATUS  mandatory
              DESCRIPTION
                      "The unit of the sensor."
              ::= { s3 3 }

	    s3valueInt OBJECT-TYPE
              SYNTAX  INTEGER
              ACCESS  read-write
              STATUS  mandatory
              DESCRIPTION
                      "The value of the sensor times 1000 as integer"
              ::= { s3 4 }

	    s3name OBJECT-TYPE
              SYNTAX  DisplayString
              ACCESS  read-only
              STATUS  mandatory
              DESCRIPTION
                      "The name of the sensor as String. 
		       This name is set by the user in the SNMP Config Table."
              ::= { s3 5 }

	    s3alarmInt OBJECT-TYPE
              SYNTAX  INTEGER
              ACCESS  read-only
              STATUS  mandatory
              DESCRIPTION
                      "The Sensor Alarm Status range 1..5 as integer"
              ::= { s3 6 }

	    s3LoLimitAlarmInt OBJECT-TYPE
              SYNTAX  INTEGER
              ACCESS  read-only
              STATUS  mandatory
              DESCRIPTION
                      "The lower limit alarm value of the sensor times 1000 as integer"
              ::= { s3 7 }

	    s3LoLimitWarnInt OBJECT-TYPE
              SYNTAX  INTEGER
              ACCESS  read-only
              STATUS  mandatory
              DESCRIPTION
                      "The lower limit warning value of the sensor times 1000 as integer"
              ::= { s3 8 }

	    s3HiLimitWarnInt OBJECT-TYPE
              SYNTAX  INTEGER
              ACCESS  read-only
              STATUS  mandatory
              DESCRIPTION
                      "The upper limit warning value of the sensor times 1000 as integer"
              ::= { s3 9 }

	    s3HiLimitAlarmInt OBJECT-TYPE
              SYNTAX  INTEGER
              ACCESS  read-only
              STATUS  mandatory
              DESCRIPTION
                      "The upper limit alarm value of the sensor times 1000 as integer"
              ::= { s3 10 }

	    s3HysterInt OBJECT-TYPE
              SYNTAX  INTEGER
              ACCESS  read-only
              STATUS  mandatory
              DESCRIPTION
                      "The hysteresis value of the sensor times 1000 as integer"
              ::= { s3 11 }


	-- sensor4:
            s4id OBJECT-TYPE
              SYNTAX  DisplayString
              ACCESS  read-only
              STATUS  mandatory
              DESCRIPTION
                      "A unique value containing sensortype and serial number."
              ::= { s4 1 }

	    s4value OBJECT-TYPE
              SYNTAX  DisplayString
              ACCESS  read-only
              STATUS  mandatory
              DESCRIPTION
                      "The value of the sensor as String."
              ::= { s4 2 }

	    s4unit OBJECT-TYPE
              SYNTAX  DisplayString
              ACCESS  read-only
              STATUS  mandatory
              DESCRIPTION
                      "The unit of the sensor."
              ::= { s4 3 }

	    s4valueInt OBJECT-TYPE
              SYNTAX  INTEGER
              ACCESS  read-write
              STATUS  mandatory
              DESCRIPTION
                      "The value of the sensor times 1000 as integer"
              ::= { s4 4 }

	    s4name OBJECT-TYPE
              SYNTAX  DisplayString
              ACCESS  read-only
              STATUS  mandatory
              DESCRIPTION
                      "The name of the sensor as String. 
		       This name is set by the user in the SNMP Config Table."
              ::= { s4 5 }

	    s4alarmInt OBJECT-TYPE
              SYNTAX  INTEGER
              ACCESS  read-only
              STATUS  mandatory
              DESCRIPTION
                      "The Sensor Alarm Status range 1..5 as integer"
              ::= { s4 6 }

	    s4LoLimitAlarmInt OBJECT-TYPE
              SYNTAX  INTEGER
              ACCESS  read-only
              STATUS  mandatory
              DESCRIPTION
                      "The lower limit alarm value of the sensor times 1000 as integer"
              ::= { s4 7 }

	    s4LoLimitWarnInt OBJECT-TYPE
              SYNTAX  INTEGER
              ACCESS  read-only
              STATUS  mandatory
              DESCRIPTION
                      "The lower limit warning value of the sensor times 1000 as integer"
              ::= { s4 8 }

	    s4HiLimitWarnInt OBJECT-TYPE
              SYNTAX  INTEGER
              ACCESS  read-only
              STATUS  mandatory
              DESCRIPTION
                      "The upper limit warning value of the sensor times 1000 as integer"
              ::= { s4 9 }

	    s4HiLimitAlarmInt OBJECT-TYPE
              SYNTAX  INTEGER
              ACCESS  read-only
              STATUS  mandatory
              DESCRIPTION
                      "The upper limit alarm value of the sensor times 1000 as integer"
              ::= { s4 10 }

	    s4HysterInt OBJECT-TYPE
              SYNTAX  INTEGER
              ACCESS  read-only
              STATUS  mandatory
              DESCRIPTION
                      "The hysteresis value of the sensor times 1000 as integer"
              ::= { s4 11 }


	-- sensor5:
            s5id OBJECT-TYPE
              SYNTAX  DisplayString
              ACCESS  read-only
              STATUS  mandatory
              DESCRIPTION
                      "A unique value containing sensortype and serial number."
              ::= { s5 1 }

	    s5value OBJECT-TYPE
              SYNTAX  DisplayString
              ACCESS  read-only
              STATUS  mandatory
              DESCRIPTION
                      "The value of the sensor as String."
              ::= { s5 2 }

	    s5unit OBJECT-TYPE
              SYNTAX  DisplayString
              ACCESS  read-only
              STATUS  mandatory
              DESCRIPTION
                      "The unit of the sensor."
              ::= { s5 3 }

	    s5valueInt OBJECT-TYPE
              SYNTAX  INTEGER
              ACCESS  read-write
              STATUS  mandatory
              DESCRIPTION
                      "The value of the sensor times 1000 as integer"
              ::= { s5 4 }

	    s5name OBJECT-TYPE
              SYNTAX  DisplayString
              ACCESS  read-only
              STATUS  mandatory
              DESCRIPTION
                      "The name of the sensor as String. 
		       This name is set by the user in the SNMP Config Table."
              ::= { s5 5 }

	    s5alarmInt OBJECT-TYPE
              SYNTAX  INTEGER
              ACCESS  read-only
              STATUS  mandatory
              DESCRIPTION
                      "The Sensor Alarm Status range 1..5 as integer"
              ::= { s5 6 }

	    s5LoLimitAlarmInt OBJECT-TYPE
              SYNTAX  INTEGER
              ACCESS  read-only
              STATUS  mandatory
              DESCRIPTION
                      "The lower limit alarm value of the sensor times 1000 as integer"
              ::= { s5 7 }

	    s5LoLimitWarnInt OBJECT-TYPE
              SYNTAX  INTEGER
              ACCESS  read-only
              STATUS  mandatory
              DESCRIPTION
                      "The lower limit warning value of the sensor times 1000 as integer"
              ::= { s5 8 }

	    s5HiLimitWarnInt OBJECT-TYPE
              SYNTAX  INTEGER
              ACCESS  read-only
              STATUS  mandatory
              DESCRIPTION
                      "The upper limit warning value of the sensor times 1000 as integer"
              ::= { s5 9 }

	    s5HiLimitAlarmInt OBJECT-TYPE
              SYNTAX  INTEGER
              ACCESS  read-only
              STATUS  mandatory
              DESCRIPTION
                      "The upper limit alarm value of the sensor times 1000 as integer"
              ::= { s5 10 }

	    s5HysterInt OBJECT-TYPE
              SYNTAX  INTEGER
              ACCESS  read-only
              STATUS  mandatory
              DESCRIPTION
                      "The hysteresis value of the sensor times 1000 as integer"
              ::= { s5 11 }


	-- sensor6:
            s6id OBJECT-TYPE
              SYNTAX  DisplayString
              ACCESS  read-only
              STATUS  mandatory
              DESCRIPTION
                      "A unique value containing sensortype and serial number."
              ::= { s6 1 }

	    s6value OBJECT-TYPE
              SYNTAX  DisplayString
              ACCESS  read-only
              STATUS  mandatory
              DESCRIPTION
                      "The value of the sensor as String."
              ::= { s6 2 }

	    s6unit OBJECT-TYPE
              SYNTAX  DisplayString
              ACCESS  read-only
              STATUS  mandatory
              DESCRIPTION
                      "The unit of the sensor."
              ::= { s6 3 }

	    s6valueInt OBJECT-TYPE
              SYNTAX  INTEGER
              ACCESS  read-write
              STATUS  mandatory
              DESCRIPTION
                      "The value of the sensor times 1000 as integer"
              ::= { s6 4 }

	    s6name OBJECT-TYPE
              SYNTAX  DisplayString
              ACCESS  read-only
              STATUS  mandatory
              DESCRIPTION
                      "The name of the sensor as String. 
		       This name is set by the user in the SNMP Config Table."
              ::= { s6 5 }

	    s6alarmInt OBJECT-TYPE
              SYNTAX  INTEGER
              ACCESS  read-only
              STATUS  mandatory
              DESCRIPTION
                      "The Sensor Alarm Status range 1..5 as integer"
              ::= { s6 6 }

	    s6LoLimitAlarmInt OBJECT-TYPE
              SYNTAX  INTEGER
              ACCESS  read-only
              STATUS  mandatory
              DESCRIPTION
                      "The lower limit alarm value of the sensor times 1000 as integer"
              ::= { s6 7 }

	    s6LoLimitWarnInt OBJECT-TYPE
              SYNTAX  INTEGER
              ACCESS  read-only
              STATUS  mandatory
              DESCRIPTION
                      "The lower limit warning value of the sensor times 1000 as integer"
              ::= { s6 8 }

	    s6HiLimitWarnInt OBJECT-TYPE
              SYNTAX  INTEGER
              ACCESS  read-only
              STATUS  mandatory
              DESCRIPTION
                      "The upper limit warning value of the sensor times 1000 as integer"
              ::= { s6 9 }

	    s6HiLimitAlarmInt OBJECT-TYPE
              SYNTAX  INTEGER
              ACCESS  read-only
              STATUS  mandatory
              DESCRIPTION
                      "The upper limit alarm value of the sensor times 1000 as integer"
              ::= { s6 10 }

	    s6HysterInt OBJECT-TYPE
              SYNTAX  INTEGER
              ACCESS  read-only
              STATUS  mandatory
              DESCRIPTION
                      "The hysteresis value of the sensor times 1000 as integer"
              ::= { s6 11 }


	-- sensor7:
            s7id OBJECT-TYPE
              SYNTAX  DisplayString
              ACCESS  read-only
              STATUS  mandatory
              DESCRIPTION
                      "A unique value containing sensortype and serial number."
              ::= { s7 1 }

	    s7value OBJECT-TYPE
              SYNTAX  DisplayString
              ACCESS  read-only
              STATUS  mandatory
              DESCRIPTION
                      "The value of the sensor as String."
              ::= { s7 2 }

	    s7unit OBJECT-TYPE
              SYNTAX  DisplayString
              ACCESS  read-only
              STATUS  mandatory
              DESCRIPTION
                      "The unit of the sensor."
              ::= { s7 3 }

	    s7valueInt OBJECT-TYPE
              SYNTAX  INTEGER
              ACCESS  read-write
              STATUS  mandatory
              DESCRIPTION
                      "The value of the sensor times 1000 as integer"
              ::= { s7 4 }

	    s7name OBJECT-TYPE
              SYNTAX  DisplayString
              ACCESS  read-only
              STATUS  mandatory
              DESCRIPTION
                      "The name of the sensor as String. 
		       This name is set by the user in the SNMP Config Table."
              ::= { s7 5 }

	    s7alarmInt OBJECT-TYPE
              SYNTAX  INTEGER
              ACCESS  read-only
              STATUS  mandatory
              DESCRIPTION
                      "The Sensor Alarm Status range 1..5 as integer"
              ::= { s7 6 }

	    s7LoLimitAlarmInt OBJECT-TYPE
              SYNTAX  INTEGER
              ACCESS  read-only
              STATUS  mandatory
              DESCRIPTION
                      "The lower limit alarm value of the sensor times 1000 as integer"
              ::= { s7 7 }

	    s7LoLimitWarnInt OBJECT-TYPE
              SYNTAX  INTEGER
              ACCESS  read-only
              STATUS  mandatory
              DESCRIPTION
                      "The lower limit warning value of the sensor times 1000 as integer"
              ::= { s7 8 }

	    s7HiLimitWarnInt OBJECT-TYPE
              SYNTAX  INTEGER
              ACCESS  read-only
              STATUS  mandatory
              DESCRIPTION
                      "The upper limit warning value of the sensor times 1000 as integer"
              ::= { s7 9 }

	    s7HiLimitAlarmInt OBJECT-TYPE
              SYNTAX  INTEGER
              ACCESS  read-only
              STATUS  mandatory
              DESCRIPTION
                      "The upper limit alarm value of the sensor times 1000 as integer"
              ::= { s7 10 }

	    s7HysterInt OBJECT-TYPE
              SYNTAX  INTEGER
              ACCESS  read-only
              STATUS  mandatory
              DESCRIPTION
                      "The hysteresis value of the sensor times 1000 as integer"
              ::= { s7 11 }


	-- sensor8:
            s8id OBJECT-TYPE
              SYNTAX  DisplayString
              ACCESS  read-only
              STATUS  mandatory
              DESCRIPTION
                      "A unique value containing sensortype and serial number."
              ::= { s8 1 }

	    s8value OBJECT-TYPE
              SYNTAX  DisplayString
              ACCESS  read-only
              STATUS  mandatory
              DESCRIPTION
                      "The value of the sensor as String."
              ::= { s8 2 }

	    s8unit OBJECT-TYPE
              SYNTAX  DisplayString
              ACCESS  read-only
              STATUS  mandatory
              DESCRIPTION
                      "The unit of the sensor."
              ::= { s8 3 }

	    s8valueInt OBJECT-TYPE
              SYNTAX  INTEGER
              ACCESS  read-write
              STATUS  mandatory
              DESCRIPTION
                      "The value of the sensor times 1000 as integer"
              ::= { s8 4 }

	    s8name OBJECT-TYPE
              SYNTAX  DisplayString
              ACCESS  read-only
              STATUS  mandatory
              DESCRIPTION
                      "The name of the sensor as String. 
		       This name is set by the user in the SNMP Config Table."
              ::= { s8 5 }

	    s8alarmInt OBJECT-TYPE
              SYNTAX  INTEGER
              ACCESS  read-only
              STATUS  mandatory
              DESCRIPTION
                      "The Sensor Alarm Status range 1..5 as integer"
              ::= { s8 6 }

	    s8LoLimitAlarmInt OBJECT-TYPE
              SYNTAX  INTEGER
              ACCESS  read-only
              STATUS  mandatory
              DESCRIPTION
                      "The lower limit alarm value of the sensor times 1000 as integer"
              ::= { s8 7 }

	    s8LoLimitWarnInt OBJECT-TYPE
              SYNTAX  INTEGER
              ACCESS  read-only
              STATUS  mandatory
              DESCRIPTION
                      "The lower limit warning value of the sensor times 1000 as integer"
              ::= { s8 8 }

	    s8HiLimitWarnInt OBJECT-TYPE
              SYNTAX  INTEGER
              ACCESS  read-only
              STATUS  mandatory
              DESCRIPTION
                      "The upper limit warning value of the sensor times 1000 as integer"
              ::= { s8 9 }

	    s8HiLimitAlarmInt OBJECT-TYPE
              SYNTAX  INTEGER
              ACCESS  read-only
              STATUS  mandatory
              DESCRIPTION
                      "The upper limit alarm value of the sensor times 1000 as integer"
              ::= { s8 10 }

	    s8HysterInt OBJECT-TYPE
              SYNTAX  INTEGER
              ACCESS  read-only
              STATUS  mandatory
              DESCRIPTION
                      "The hysteresis value of the sensor times 1000 as integer"
              ::= { s8 11 }


	-- sensor9:
            s9id OBJECT-TYPE
              SYNTAX  DisplayString
              ACCESS  read-only
              STATUS  mandatory
              DESCRIPTION
                      "A unique value containing sensortype and serial number."
              ::= { s9 1 }

	    s9value OBJECT-TYPE
              SYNTAX  DisplayString
              ACCESS  read-only
              STATUS  mandatory
              DESCRIPTION
                      "The value of the sensor as String."
              ::= { s9 2 }

	    s9unit OBJECT-TYPE
              SYNTAX  DisplayString
              ACCESS  read-only
              STATUS  mandatory
              DESCRIPTION
                      "The unit of the sensor."
              ::= { s9 3 }

	    s9valueInt OBJECT-TYPE
              SYNTAX  INTEGER
              ACCESS  read-write
              STATUS  mandatory
              DESCRIPTION
                      "The value of the sensor times 1000 as integer"
              ::= { s9 4 }

	    s9name OBJECT-TYPE
              SYNTAX  DisplayString
              ACCESS  read-only
              STATUS  mandatory
              DESCRIPTION
                      "The name of the sensor as String. 
		       This name is set by the user in the SNMP Config Table."
              ::= { s9 5 }

	    s9alarmInt OBJECT-TYPE
              SYNTAX  INTEGER
              ACCESS  read-only
              STATUS  mandatory
              DESCRIPTION
                      "The Sensor Alarm Status range 1..5 as integer"
              ::= { s9 6 }

	    s9LoLimitAlarmInt OBJECT-TYPE
              SYNTAX  INTEGER
              ACCESS  read-only
              STATUS  mandatory
              DESCRIPTION
                      "The lower limit alarm value of the sensor times 1000 as integer"
              ::= { s9 7 }

	    s9LoLimitWarnInt OBJECT-TYPE
              SYNTAX  INTEGER
              ACCESS  read-only
              STATUS  mandatory
              DESCRIPTION
                      "The lower limit warning value of the sensor times 1000 as integer"
              ::= { s9 8 }

	    s9HiLimitWarnInt OBJECT-TYPE
              SYNTAX  INTEGER
              ACCESS  read-only
              STATUS  mandatory
              DESCRIPTION
                      "The upper limit warning value of the sensor times 1000 as integer"
              ::= { s9 9 }

	    s9HiLimitAlarmInt OBJECT-TYPE
              SYNTAX  INTEGER
              ACCESS  read-only
              STATUS  mandatory
              DESCRIPTION
                      "The upper limit alarm value of the sensor times 1000 as integer"
              ::= { s9 10 }

	    s9HysterInt OBJECT-TYPE
              SYNTAX  INTEGER
              ACCESS  read-only
              STATUS  mandatory
              DESCRIPTION
                      "The hysteresis value of the sensor times 1000 as integer"
              ::= { s9 11 }


	-- sensor10:
            s10id OBJECT-TYPE
              SYNTAX  DisplayString
              ACCESS  read-only
              STATUS  mandatory
              DESCRIPTION
                      "A unique value containing sensortype and serial number."
              ::= { s10 1 }

	    s10value OBJECT-TYPE
              SYNTAX  DisplayString
              ACCESS  read-only
              STATUS  mandatory
              DESCRIPTION
                      "The value of the sensor as String."
              ::= { s10 2 }

	    s10unit OBJECT-TYPE
              SYNTAX  DisplayString
              ACCESS  read-only
              STATUS  mandatory
              DESCRIPTION
                      "The unit of the sensor."
              ::= { s10 3 }

	    s10valueInt OBJECT-TYPE
              SYNTAX  INTEGER
              ACCESS  read-write
              STATUS  mandatory
              DESCRIPTION
                      "The value of the sensor times 1000 as integer"
              ::= { s10 4 }

	    s10name OBJECT-TYPE
              SYNTAX  DisplayString
              ACCESS  read-only
              STATUS  mandatory
              DESCRIPTION
                      "The name of the sensor as String. 
		       This name is set by the user in the SNMP Config Table."
              ::= { s10 5 }

	    s10alarmInt OBJECT-TYPE
              SYNTAX  INTEGER
              ACCESS  read-only
              STATUS  mandatory
              DESCRIPTION
                      "The Sensor Alarm Status range 1..5 as integer"
              ::= { s10 6 }

	    s10LoLimitAlarmInt OBJECT-TYPE
              SYNTAX  INTEGER
              ACCESS  read-only
              STATUS  mandatory
              DESCRIPTION
                      "The lower limit alarm value of the sensor times 1000 as integer"
              ::= { s10 7 }

	    s10LoLimitWarnInt OBJECT-TYPE
              SYNTAX  INTEGER
              ACCESS  read-only
              STATUS  mandatory
              DESCRIPTION
                      "The lower limit warning value of the sensor times 1000 as integer"
              ::= { s10 8 }

	    s10HiLimitWarnInt OBJECT-TYPE
              SYNTAX  INTEGER
              ACCESS  read-only
              STATUS  mandatory
              DESCRIPTION
                      "The upper limit warning value of the sensor times 1000 as integer"
              ::= { s10 9 }

	    s10HiLimitAlarmInt OBJECT-TYPE
              SYNTAX  INTEGER
              ACCESS  read-only
              STATUS  mandatory
              DESCRIPTION
                      "The upper limit alarm value of the sensor times 1000 as integer"
              ::= { s10 10 }

	    s10HysterInt OBJECT-TYPE
              SYNTAX  INTEGER
              ACCESS  read-only
              STATUS  mandatory
              DESCRIPTION
                      "The hysteresis value of the sensor times 1000 as integer"
              ::= { s10 11 }


  --  11 - 20
	-- sensor11:
            s11id OBJECT-TYPE
              SYNTAX  DisplayString
              ACCESS  read-only
              STATUS  mandatory
              DESCRIPTION
                      "A unique value containing sensortype and serial number."
              ::= { s11 1 }

	    s11value OBJECT-TYPE
              SYNTAX  DisplayString
              ACCESS  read-only
              STATUS  mandatory
              DESCRIPTION
                      "The value of the sensor as String."
              ::= { s11 2 }

	    s11unit OBJECT-TYPE
              SYNTAX  DisplayString
              ACCESS  read-only
              STATUS  mandatory
              DESCRIPTION
                      "The unit of the sensor."
              ::= { s11 3 }

	    s11valueInt OBJECT-TYPE
              SYNTAX  INTEGER
              ACCESS  read-write
              STATUS  mandatory
              DESCRIPTION
                      "The value of the sensor times 1000 as integer"
              ::= { s11 4 }

	    s11name OBJECT-TYPE
              SYNTAX  DisplayString
              ACCESS  read-only
              STATUS  mandatory
              DESCRIPTION
                      "The name of the sensor as String. 
		       This name is set by the user in the SNMP Config Table."
              ::= { s11 5 }

	    s11alarmInt OBJECT-TYPE
              SYNTAX  INTEGER
              ACCESS  read-only
              STATUS  mandatory
              DESCRIPTION
                      "The Sensor Alarm Status range 1..5 as integer"
              ::= { s11 6 }

	    s11LoLimitAlarmInt OBJECT-TYPE
              SYNTAX  INTEGER
              ACCESS  read-only
              STATUS  mandatory
              DESCRIPTION
                      "The lower limit alarm value of the sensor times 1000 as integer"
              ::= { s11 7 }

	    s11LoLimitWarnInt OBJECT-TYPE
              SYNTAX  INTEGER
              ACCESS  read-only
              STATUS  mandatory
              DESCRIPTION
                      "The lower limit warning value of the sensor times 1000 as integer"
              ::= { s11 8 }

	    s11HiLimitWarnInt OBJECT-TYPE
              SYNTAX  INTEGER
              ACCESS  read-only
              STATUS  mandatory
              DESCRIPTION
                      "The upper limit warning value of the sensor times 1000 as integer"
              ::= { s11 9 }

	    s11HiLimitAlarmInt OBJECT-TYPE
              SYNTAX  INTEGER
              ACCESS  read-only
              STATUS  mandatory
              DESCRIPTION
                      "The upper limit alarm value of the sensor times 1000 as integer"
              ::= { s11 10 }

	    s11HysterInt OBJECT-TYPE
              SYNTAX  INTEGER
              ACCESS  read-only
              STATUS  mandatory
              DESCRIPTION
                      "The hysteresis value of the sensor times 1000 as integer"
              ::= { s11 11 }


	-- sensor12:
            s12id OBJECT-TYPE
              SYNTAX  DisplayString
              ACCESS  read-only
              STATUS  mandatory
              DESCRIPTION
                      "A unique value containing sensortype and serial number."
              ::= { s12 1 }

	    s12value OBJECT-TYPE
              SYNTAX  DisplayString
              ACCESS  read-only
              STATUS  mandatory
              DESCRIPTION
                      "The value of the sensor as String."
              ::= { s12 2 }

	    s12unit OBJECT-TYPE
              SYNTAX  DisplayString
              ACCESS  read-only
              STATUS  mandatory
              DESCRIPTION
                      "The unit of the sensor."
              ::= { s12 3 }

	    s12valueInt OBJECT-TYPE
              SYNTAX  INTEGER
              ACCESS  read-write
              STATUS  mandatory
              DESCRIPTION
                      "The value of the sensor times 1000 as integer"
              ::= { s12 4 }

	    s12name OBJECT-TYPE
              SYNTAX  DisplayString
              ACCESS  read-only
              STATUS  mandatory
              DESCRIPTION
                      "The name of the sensor as String. 
		       This name is set by the user in the SNMP Config Table."
              ::= { s12 5 }

	    s12alarmInt OBJECT-TYPE
              SYNTAX  INTEGER
              ACCESS  read-only
              STATUS  mandatory
              DESCRIPTION
                      "The Sensor Alarm Status range 1..5 as integer"
              ::= { s12 6 }

	    s12LoLimitAlarmInt OBJECT-TYPE
              SYNTAX  INTEGER
              ACCESS  read-only
              STATUS  mandatory
              DESCRIPTION
                      "The lower limit alarm value of the sensor times 1000 as integer"
              ::= { s12 7 }

	    s12LoLimitWarnInt OBJECT-TYPE
              SYNTAX  INTEGER
              ACCESS  read-only
              STATUS  mandatory
              DESCRIPTION
                      "The lower limit warning value of the sensor times 1000 as integer"
              ::= { s12 8 }

	    s12HiLimitWarnInt OBJECT-TYPE
              SYNTAX  INTEGER
              ACCESS  read-only
              STATUS  mandatory
              DESCRIPTION
                      "The upper limit warning value of the sensor times 1000 as integer"
              ::= { s12 9 }

	    s12HiLimitAlarmInt OBJECT-TYPE
              SYNTAX  INTEGER
              ACCESS  read-only
              STATUS  mandatory
              DESCRIPTION
                      "The upper limit alarm value of the sensor times 1000 as integer"
              ::= { s12 10 }

	    s12HysterInt OBJECT-TYPE
              SYNTAX  INTEGER
              ACCESS  read-only
              STATUS  mandatory
              DESCRIPTION
                      "The hysteresis value of the sensor times 1000 as integer"
              ::= { s12 11 }


	-- sensor13:
            s13id OBJECT-TYPE
              SYNTAX  DisplayString
              ACCESS  read-only
              STATUS  mandatory
              DESCRIPTION
                      "A unique value containing sensortype and serial number."
              ::= { s13 1 }

	    s13value OBJECT-TYPE
              SYNTAX  DisplayString
              ACCESS  read-only
              STATUS  mandatory
              DESCRIPTION
                      "The value of the sensor as String."
              ::= { s13 2 }

	    s13unit OBJECT-TYPE
              SYNTAX  DisplayString
              ACCESS  read-only
              STATUS  mandatory
              DESCRIPTION
                      "The unit of the sensor."
              ::= { s13 3 }

	    s13valueInt OBJECT-TYPE
              SYNTAX  INTEGER
              ACCESS  read-write
              STATUS  mandatory
              DESCRIPTION
                      "The value of the sensor times 1000 as integer"
              ::= { s13 4 }

	    s13name OBJECT-TYPE
              SYNTAX  DisplayString
              ACCESS  read-only
              STATUS  mandatory
              DESCRIPTION
                      "The name of the sensor as String. 
		       This name is set by the user in the SNMP Config Table."
              ::= { s13 5 }

	    s13alarmInt OBJECT-TYPE
              SYNTAX  INTEGER
              ACCESS  read-only
              STATUS  mandatory
              DESCRIPTION
                      "The Sensor Alarm Status range 1..5 as integer"
              ::= { s13 6 }

	    s13LoLimitAlarmInt OBJECT-TYPE
              SYNTAX  INTEGER
              ACCESS  read-only
              STATUS  mandatory
              DESCRIPTION
                      "The lower limit alarm value of the sensor times 1000 as integer"
              ::= { s13 7 }

	    s13LoLimitWarnInt OBJECT-TYPE
              SYNTAX  INTEGER
              ACCESS  read-only
              STATUS  mandatory
              DESCRIPTION
                      "The lower limit warning value of the sensor times 1000 as integer"
              ::= { s13 8 }

	    s13HiLimitWarnInt OBJECT-TYPE
              SYNTAX  INTEGER
              ACCESS  read-only
              STATUS  mandatory
              DESCRIPTION
                      "The upper limit warning value of the sensor times 1000 as integer"
              ::= { s13 9 }

	    s13HiLimitAlarmInt OBJECT-TYPE
              SYNTAX  INTEGER
              ACCESS  read-only
              STATUS  mandatory
              DESCRIPTION
                      "The upper limit alarm value of the sensor times 1000 as integer"
              ::= { s13 10 }

	    s13HysterInt OBJECT-TYPE
              SYNTAX  INTEGER
              ACCESS  read-only
              STATUS  mandatory
              DESCRIPTION
                      "The hysteresis value of the sensor times 1000 as integer"
              ::= { s13 11 }


	-- sensor14:
            s14id OBJECT-TYPE
              SYNTAX  DisplayString
              ACCESS  read-only
              STATUS  mandatory
              DESCRIPTION
                      "A unique value containing sensor1type and serial number."
              ::= { s14 1 }

	    s14value OBJECT-TYPE
              SYNTAX  DisplayString
              ACCESS  read-only
              STATUS  mandatory
              DESCRIPTION
                      "The value of the sensor as String."
              ::= { s14 2 }

	    s14unit OBJECT-TYPE
              SYNTAX  DisplayString
              ACCESS  read-only
              STATUS  mandatory
              DESCRIPTION
                      "The unit of the sensor."
              ::= { s14 3 }

	    s14valueInt OBJECT-TYPE
              SYNTAX  INTEGER
              ACCESS  read-write
              STATUS  mandatory
              DESCRIPTION
                      "The value of the sensor times 1000 as integer"
              ::= { s14 4 }

	    s14name OBJECT-TYPE
              SYNTAX  DisplayString
              ACCESS  read-only
              STATUS  mandatory
              DESCRIPTION
                      "The name of the sensor as String. 
		       This name is set by the user in the SNMP Config Table."
              ::= { s14 5 }

	    s14alarmInt OBJECT-TYPE
              SYNTAX  INTEGER
              ACCESS  read-only
              STATUS  mandatory
              DESCRIPTION
                      "The Sensor Alarm Status range 1..5 as integer"
              ::= { s14 6 }

	    s14LoLimitAlarmInt OBJECT-TYPE
              SYNTAX  INTEGER
              ACCESS  read-only
              STATUS  mandatory
              DESCRIPTION
                      "The lower limit alarm value of the sensor times 1000 as integer"
              ::= { s14 7 }

	    s14LoLimitWarnInt OBJECT-TYPE
              SYNTAX  INTEGER
              ACCESS  read-only
              STATUS  mandatory
              DESCRIPTION
                      "The lower limit warning value of the sensor times 1000 as integer"
              ::= { s14 8 }

	    s14HiLimitWarnInt OBJECT-TYPE
              SYNTAX  INTEGER
              ACCESS  read-only
              STATUS  mandatory
              DESCRIPTION
                      "The upper limit warning value of the sensor times 1000 as integer"
              ::= { s14 9 }

	    s14HiLimitAlarmInt OBJECT-TYPE
              SYNTAX  INTEGER
              ACCESS  read-only
              STATUS  mandatory
              DESCRIPTION
                      "The upper limit alarm value of the sensor times 1000 as integer"
              ::= { s14 10 }

	    s14HysterInt OBJECT-TYPE
              SYNTAX  INTEGER
              ACCESS  read-only
              STATUS  mandatory
              DESCRIPTION
                      "The hysteresis value of the sensor times 1000 as integer"
              ::= { s14 11 }


	-- sensor15:
            s15id OBJECT-TYPE
              SYNTAX  DisplayString
              ACCESS  read-only
              STATUS  mandatory
              DESCRIPTION
                      "A unique value containing sensortype and serial number."
              ::= { s15 1 }

	    s15value OBJECT-TYPE
              SYNTAX  DisplayString
              ACCESS  read-only
              STATUS  mandatory
              DESCRIPTION
                      "The value of the sensor as String."
              ::= { s15 2 }

	    s15unit OBJECT-TYPE
              SYNTAX  DisplayString
              ACCESS  read-only
              STATUS  mandatory
              DESCRIPTION
                      "The unit of the sensor."
              ::= { s15 3 }

	    s15valueInt OBJECT-TYPE
              SYNTAX  INTEGER
              ACCESS  read-write
              STATUS  mandatory
              DESCRIPTION
                      "The value of the sensor times 1000 as integer"
              ::= { s15 4 }

	    s15name OBJECT-TYPE
              SYNTAX  DisplayString
              ACCESS  read-only
              STATUS  mandatory
              DESCRIPTION
                      "The name of the sensor as String. 
		       This name is set by the user in the SNMP Config Table."
              ::= { s15 5 }

	    s15alarmInt OBJECT-TYPE
              SYNTAX  INTEGER
              ACCESS  read-only
              STATUS  mandatory
              DESCRIPTION
                      "The Sensor Alarm Status range 1..5 as integer"
              ::= { s15 6 }

	    s15LoLimitAlarmInt OBJECT-TYPE
              SYNTAX  INTEGER
              ACCESS  read-only
              STATUS  mandatory
              DESCRIPTION
                      "The lower limit alarm value of the sensor times 1000 as integer"
              ::= { s15 7 }

	    s15LoLimitWarnInt OBJECT-TYPE
              SYNTAX  INTEGER
              ACCESS  read-only
              STATUS  mandatory
              DESCRIPTION
                      "The lower limit warning value of the sensor times 1000 as integer"
              ::= { s15 8 }

	    s15HiLimitWarnInt OBJECT-TYPE
              SYNTAX  INTEGER
              ACCESS  read-only
              STATUS  mandatory
              DESCRIPTION
                      "The upper limit warning value of the sensor times 1000 as integer"
              ::= { s15 9 }

	    s15HiLimitAlarmInt OBJECT-TYPE
              SYNTAX  INTEGER
              ACCESS  read-only
              STATUS  mandatory
              DESCRIPTION
                      "The upper limit alarm value of the sensor times 1000 as integer"
              ::= { s15 10 }

	    s15HysterInt OBJECT-TYPE
              SYNTAX  INTEGER
              ACCESS  read-only
              STATUS  mandatory
              DESCRIPTION
                      "The hysteresis value of the sensor times 1000 as integer"
              ::= { s15 11 }


	-- sensor16:
            s16id OBJECT-TYPE
              SYNTAX  DisplayString
              ACCESS  read-only
              STATUS  mandatory
              DESCRIPTION
                      "A unique value containing sensortype and serial number."
              ::= { s16 1 }

	    s16value OBJECT-TYPE
              SYNTAX  DisplayString
              ACCESS  read-only
              STATUS  mandatory
              DESCRIPTION
                      "The value of the sensor as String."
              ::= { s16 2 }

	    s16unit OBJECT-TYPE
              SYNTAX  DisplayString
              ACCESS  read-only
              STATUS  mandatory
              DESCRIPTION
                      "The unit of the sensor."
              ::= { s16 3 }

	    s16valueInt OBJECT-TYPE
              SYNTAX  INTEGER
              ACCESS  read-write
              STATUS  mandatory
              DESCRIPTION
                      "The value of the sensor times 1000 as integer"
              ::= { s16 4 }

	    s16name OBJECT-TYPE
              SYNTAX  DisplayString
              ACCESS  read-only
              STATUS  mandatory
              DESCRIPTION
                      "The name of the sensor as String. 
		       This name is set by the user in the SNMP Config Table."
              ::= { s16 5 }

	    s16alarmInt OBJECT-TYPE
              SYNTAX  INTEGER
              ACCESS  read-only
              STATUS  mandatory
              DESCRIPTION
                      "The Sensor Alarm Status range 1..5 as integer"
              ::= { s16 6 }

	    s16LoLimitAlarmInt OBJECT-TYPE
              SYNTAX  INTEGER
              ACCESS  read-only
              STATUS  mandatory
              DESCRIPTION
                      "The lower limit alarm value of the sensor times 1000 as integer"
              ::= { s16 7 }

	    s16LoLimitWarnInt OBJECT-TYPE
              SYNTAX  INTEGER
              ACCESS  read-only
              STATUS  mandatory
              DESCRIPTION
                      "The lower limit warning value of the sensor times 1000 as integer"
              ::= { s16 8 }

	    s16HiLimitWarnInt OBJECT-TYPE
              SYNTAX  INTEGER
              ACCESS  read-only
              STATUS  mandatory
              DESCRIPTION
                      "The upper limit warning value of the sensor times 1000 as integer"
              ::= { s16 9 }

	    s16HiLimitAlarmInt OBJECT-TYPE
              SYNTAX  INTEGER
              ACCESS  read-only
              STATUS  mandatory
              DESCRIPTION
                      "The upper limit alarm value of the sensor times 1000 as integer"
              ::= { s16 10 }

	    s16HysterInt OBJECT-TYPE
              SYNTAX  INTEGER
              ACCESS  read-only
              STATUS  mandatory
              DESCRIPTION
                      "The hysteresis value of the sensor times 1000 as integer"
              ::= { s16 11 }


	-- sensor17:
            s17id OBJECT-TYPE
              SYNTAX  DisplayString
              ACCESS  read-only
              STATUS  mandatory
              DESCRIPTION
                      "A unique value containing sensortype and serial number."
              ::= { s17 1 }

	    s17value OBJECT-TYPE
              SYNTAX  DisplayString
              ACCESS  read-only
              STATUS  mandatory
              DESCRIPTION
                      "The value of the sensor as String."
              ::= { s17 2 }

	    s17unit OBJECT-TYPE
              SYNTAX  DisplayString
              ACCESS  read-only
              STATUS  mandatory
              DESCRIPTION
                      "The unit of the sensor."
              ::= { s17 3 }

	    s17valueInt OBJECT-TYPE
              SYNTAX  INTEGER
              ACCESS  read-write
              STATUS  mandatory
              DESCRIPTION
                      "The value of the sensor times 1000 as integer"
              ::= { s17 4 }

	    s17name OBJECT-TYPE
              SYNTAX  DisplayString
              ACCESS  read-only
              STATUS  mandatory
              DESCRIPTION
                      "The name of the sensor as String. 
		       This name is set by the user in the SNMP Config Table."
              ::= { s17 5 }

	    s17alarmInt OBJECT-TYPE
              SYNTAX  INTEGER
              ACCESS  read-only
              STATUS  mandatory
              DESCRIPTION
                      "The Sensor Alarm Status range 1..5 as integer"
              ::= { s17 6 }

	    s17LoLimitAlarmInt OBJECT-TYPE
              SYNTAX  INTEGER
              ACCESS  read-only
              STATUS  mandatory
              DESCRIPTION
                      "The lower limit alarm value of the sensor times 1000 as integer"
              ::= { s17 7 }

	    s17LoLimitWarnInt OBJECT-TYPE
              SYNTAX  INTEGER
              ACCESS  read-only
              STATUS  mandatory
              DESCRIPTION
                      "The lower limit warning value of the sensor times 1000 as integer"
              ::= { s17 8 }

	    s17HiLimitWarnInt OBJECT-TYPE
              SYNTAX  INTEGER
              ACCESS  read-only
              STATUS  mandatory
              DESCRIPTION
                      "The upper limit warning value of the sensor times 1000 as integer"
              ::= { s17 9 }

	    s17HiLimitAlarmInt OBJECT-TYPE
              SYNTAX  INTEGER
              ACCESS  read-only
              STATUS  mandatory
              DESCRIPTION
                      "The upper limit alarm value of the sensor times 1000 as integer"
              ::= { s17 10 }

	    s17HysterInt OBJECT-TYPE
              SYNTAX  INTEGER
              ACCESS  read-only
              STATUS  mandatory
              DESCRIPTION
                      "The hysteresis value of the sensor times 1000 as integer"
              ::= { s17 11 }


	-- sensor18:
            s18id OBJECT-TYPE
              SYNTAX  DisplayString
              ACCESS  read-only
              STATUS  mandatory
              DESCRIPTION
                      "A unique value containing sensortype and serial number."
              ::= { s18 1 }

	    s18value OBJECT-TYPE
              SYNTAX  DisplayString
              ACCESS  read-only
              STATUS  mandatory
              DESCRIPTION
                      "The value of the sensor as String."
              ::= { s18 2 }

	    s18unit OBJECT-TYPE
              SYNTAX  DisplayString
              ACCESS  read-only
              STATUS  mandatory
              DESCRIPTION
                      "The unit of the sensor."
              ::= { s18 3 }

	    s18valueInt OBJECT-TYPE
              SYNTAX  INTEGER
              ACCESS  read-write
              STATUS  mandatory
              DESCRIPTION
                      "The value of the sensor times 1000 as integer"
              ::= { s18 4 }

	    s18name OBJECT-TYPE
              SYNTAX  DisplayString
              ACCESS  read-only
              STATUS  mandatory
              DESCRIPTION
                      "The name of the sensor as String. 
		       This name is set by the user in the SNMP Config Table."
              ::= { s18 5 }

	    s18alarmInt OBJECT-TYPE
              SYNTAX  INTEGER
              ACCESS  read-only
              STATUS  mandatory
              DESCRIPTION
                      "The Sensor Alarm Status range 1..5 as integer"
              ::= { s18 6 }

	    s18LoLimitAlarmInt OBJECT-TYPE
              SYNTAX  INTEGER
              ACCESS  read-only
              STATUS  mandatory
              DESCRIPTION
                      "The lower limit alarm value of the sensor times 1000 as integer"
              ::= { s18 7 }

	    s18LoLimitWarnInt OBJECT-TYPE
              SYNTAX  INTEGER
              ACCESS  read-only
              STATUS  mandatory
              DESCRIPTION
                      "The lower limit warning value of the sensor times 1000 as integer"
              ::= { s18 8 }

	    s18HiLimitWarnInt OBJECT-TYPE
              SYNTAX  INTEGER
              ACCESS  read-only
              STATUS  mandatory
              DESCRIPTION
                      "The upper limit warning value of the sensor times 1000 as integer"
              ::= { s18 9 }

	    s18HiLimitAlarmInt OBJECT-TYPE
              SYNTAX  INTEGER
              ACCESS  read-only
              STATUS  mandatory
              DESCRIPTION
                      "The upper limit alarm value of the sensor times 1000 as integer"
              ::= { s18 10 }

	    s18HysterInt OBJECT-TYPE
              SYNTAX  INTEGER
              ACCESS  read-only
              STATUS  mandatory
              DESCRIPTION
                      "The hysteresis value of the sensor times 1000 as integer"
              ::= { s18 11 }


	-- sensor19:
            s19id OBJECT-TYPE
              SYNTAX  DisplayString
              ACCESS  read-only
              STATUS  mandatory
              DESCRIPTION
                      "A unique value containing sensortype and serial number."
              ::= { s19 1 }

	    s19value OBJECT-TYPE
              SYNTAX  DisplayString
              ACCESS  read-only
              STATUS  mandatory
              DESCRIPTION
                      "The value of the sensor as String."
              ::= { s19 2 }

	    s19unit OBJECT-TYPE
              SYNTAX  DisplayString
              ACCESS  read-only
              STATUS  mandatory
              DESCRIPTION
                      "The unit of the sensor."
              ::= { s19 3 }

	    s19valueInt OBJECT-TYPE
              SYNTAX  INTEGER
              ACCESS  read-write
              STATUS  mandatory
              DESCRIPTION
                      "The value of the sensor times 1000 as integer"
              ::= { s19 4 }

	    s19name OBJECT-TYPE
              SYNTAX  DisplayString
              ACCESS  read-only
              STATUS  mandatory
              DESCRIPTION
                      "The name of the sensor as String. 
		       This name is set by the user in the SNMP Config Table."
              ::= { s19 5 }

	    s19alarmInt OBJECT-TYPE
              SYNTAX  INTEGER
              ACCESS  read-only
              STATUS  mandatory
              DESCRIPTION
                      "The Sensor Alarm Status range 1..5 as integer"
              ::= { s19 6 }

	    s19LoLimitAlarmInt OBJECT-TYPE
              SYNTAX  INTEGER
              ACCESS  read-only
              STATUS  mandatory
              DESCRIPTION
                      "The lower limit alarm value of the sensor times 1000 as integer"
              ::= { s19 7 }

	    s19LoLimitWarnInt OBJECT-TYPE
              SYNTAX  INTEGER
              ACCESS  read-only
              STATUS  mandatory
              DESCRIPTION
                      "The lower limit warning value of the sensor times 1000 as integer"
              ::= { s19 8 }

	    s19HiLimitWarnInt OBJECT-TYPE
              SYNTAX  INTEGER
              ACCESS  read-only
              STATUS  mandatory
              DESCRIPTION
                      "The upper limit warning value of the sensor times 1000 as integer"
              ::= { s19 9 }

	    s19HiLimitAlarmInt OBJECT-TYPE
              SYNTAX  INTEGER
              ACCESS  read-only
              STATUS  mandatory
              DESCRIPTION
                      "The upper limit alarm value of the sensor times 1000 as integer"
              ::= { s19 10 }

	    s19HysterInt OBJECT-TYPE
              SYNTAX  INTEGER
              ACCESS  read-only
              STATUS  mandatory
              DESCRIPTION
                      "The hysteresis value of the sensor times 1000 as integer"
              ::= { s19 11 }


	-- sensor20:
            s20id OBJECT-TYPE
              SYNTAX  DisplayString
              ACCESS  read-only
              STATUS  mandatory
              DESCRIPTION
                      "A unique value containing sensortype and serial number."
              ::= { s20 1 }

	    s20value OBJECT-TYPE
              SYNTAX  DisplayString
              ACCESS  read-only
              STATUS  mandatory
              DESCRIPTION
                      "The value of the sensor as String."
              ::= { s20 2 }

	    s20unit OBJECT-TYPE
              SYNTAX  DisplayString
              ACCESS  read-only
              STATUS  mandatory
              DESCRIPTION
                      "The unit of the sensor."
              ::= { s20 3 }

	    s20valueInt OBJECT-TYPE
              SYNTAX  INTEGER
              ACCESS  read-write
              STATUS  mandatory
              DESCRIPTION
                      "The value of the sensor times 1000 as integer"
              ::= { s20 4 }

	    s20name OBJECT-TYPE
              SYNTAX  DisplayString
              ACCESS  read-only
              STATUS  mandatory
              DESCRIPTION
                      "The name of the sensor as String. 
		       This name is set by the user in the SNMP Config Table."
              ::= { s20 5 }

	    s20alarmInt OBJECT-TYPE
              SYNTAX  INTEGER
              ACCESS  read-only
              STATUS  mandatory
              DESCRIPTION
                      "The Sensor Alarm Status range 1..5 as integer"
              ::= { s20 6 }

	    s20LoLimitAlarmInt OBJECT-TYPE
              SYNTAX  INTEGER
              ACCESS  read-only
              STATUS  mandatory
              DESCRIPTION
                      "The lower limit alarm value of the sensor times 1000 as integer"
              ::= { s20 7 }

	    s20LoLimitWarnInt OBJECT-TYPE
              SYNTAX  INTEGER
              ACCESS  read-only
              STATUS  mandatory
              DESCRIPTION
                      "The lower limit warning value of the sensor times 1000 as integer"
              ::= { s20 8 }

	    s20HiLimitWarnInt OBJECT-TYPE
              SYNTAX  INTEGER
              ACCESS  read-only
              STATUS  mandatory
              DESCRIPTION
                      "The upper limit warning value of the sensor times 1000 as integer"
              ::= { s20 9 }

	    s20HiLimitAlarmInt OBJECT-TYPE
              SYNTAX  INTEGER
              ACCESS  read-only
              STATUS  mandatory
              DESCRIPTION
                      "The upper limit alarm value of the sensor times 1000 as integer"
              ::= { s20 10 }

	    s20HysterInt OBJECT-TYPE
              SYNTAX  INTEGER
              ACCESS  read-only
              STATUS  mandatory
              DESCRIPTION
                      "The hysteresis value of the sensor times 1000 as integer"
              ::= { s20 11 }


  --  21 - 30
	-- sensor21:
            s21id OBJECT-TYPE
              SYNTAX  DisplayString
              ACCESS  read-only
              STATUS  mandatory
              DESCRIPTION
                      "A unique value containing sensortype and serial number."
              ::= { s21 1 }

	    s21value OBJECT-TYPE
              SYNTAX  DisplayString
              ACCESS  read-only
              STATUS  mandatory
              DESCRIPTION
                      "The value of the sensor as String."
              ::= { s21 2 }

	    s21unit OBJECT-TYPE
              SYNTAX  DisplayString
              ACCESS  read-only
              STATUS  mandatory
              DESCRIPTION
                      "The unit of the sensor."
              ::= { s21 3 }

	    s21valueInt OBJECT-TYPE
              SYNTAX  INTEGER
              ACCESS  read-write
              STATUS  mandatory
              DESCRIPTION
                      "The value of the sensor times 1000 as integer"
              ::= { s21 4 }

	    s21name OBJECT-TYPE
              SYNTAX  DisplayString
              ACCESS  read-only
              STATUS  mandatory
              DESCRIPTION
                      "The name of the sensor as String. 
		       This name is set by the user in the SNMP Config Table."
              ::= { s21 5 }

	    s21alarmInt OBJECT-TYPE
              SYNTAX  INTEGER
              ACCESS  read-only
              STATUS  mandatory
              DESCRIPTION
                      "The Sensor Alarm Status range 1..5 as integer"
              ::= { s21 6 }

	    s21LoLimitAlarmInt OBJECT-TYPE
              SYNTAX  INTEGER
              ACCESS  read-only
              STATUS  mandatory
              DESCRIPTION
                      "The lower limit alarm value of the sensor times 1000 as integer"
              ::= { s21 7 }

	    s21LoLimitWarnInt OBJECT-TYPE
              SYNTAX  INTEGER
              ACCESS  read-only
              STATUS  mandatory
              DESCRIPTION
                      "The lower limit warning value of the sensor times 1000 as integer"
              ::= { s21 8 }

	    s21HiLimitWarnInt OBJECT-TYPE
              SYNTAX  INTEGER
              ACCESS  read-only
              STATUS  mandatory
              DESCRIPTION
                      "The upper limit warning value of the sensor times 1000 as integer"
              ::= { s21 9 }

	    s21HiLimitAlarmInt OBJECT-TYPE
              SYNTAX  INTEGER
              ACCESS  read-only
              STATUS  mandatory
              DESCRIPTION
                      "The upper limit alarm value of the sensor times 1000 as integer"
              ::= { s21 10 }

	    s21HysterInt OBJECT-TYPE
              SYNTAX  INTEGER
              ACCESS  read-only
              STATUS  mandatory
              DESCRIPTION
                      "The hysteresis value of the sensor times 1000 as integer"
              ::= { s21 11 }


	-- sensor22:
            s22id OBJECT-TYPE
              SYNTAX  DisplayString
              ACCESS  read-only
              STATUS  mandatory
              DESCRIPTION
                      "A unique value containing sensortype and serial number."
              ::= { s22 1 }

	    s22value OBJECT-TYPE
              SYNTAX  DisplayString
              ACCESS  read-only
              STATUS  mandatory
              DESCRIPTION
                      "The value of the sensor as String."
              ::= { s22 2 }

	    s22unit OBJECT-TYPE
              SYNTAX  DisplayString
              ACCESS  read-only
              STATUS  mandatory
              DESCRIPTION
                      "The unit of the sensor."
              ::= { s22 3 }

	    s22valueInt OBJECT-TYPE
              SYNTAX  INTEGER
              ACCESS  read-write
              STATUS  mandatory
              DESCRIPTION
                      "The value of the sensor times 1000 as integer"
              ::= { s22 4 }

	    s22name OBJECT-TYPE
              SYNTAX  DisplayString
              ACCESS  read-only
              STATUS  mandatory
              DESCRIPTION
                      "The name of the sensor as String. 
		       This name is set by the user in the SNMP Config Table."
              ::= { s22 5 }

	    s22alarmInt OBJECT-TYPE
              SYNTAX  INTEGER
              ACCESS  read-only
              STATUS  mandatory
              DESCRIPTION
                      "The Sensor Alarm Status range 1..5 as integer"
              ::= { s22 6 }

	    s22LoLimitAlarmInt OBJECT-TYPE
              SYNTAX  INTEGER
              ACCESS  read-only
              STATUS  mandatory
              DESCRIPTION
                      "The lower limit alarm value of the sensor times 1000 as integer"
              ::= { s22 7 }

	    s22LoLimitWarnInt OBJECT-TYPE
              SYNTAX  INTEGER
              ACCESS  read-only
              STATUS  mandatory
              DESCRIPTION
                      "The lower limit warning value of the sensor times 1000 as integer"
              ::= { s22 8 }

	    s22HiLimitWarnInt OBJECT-TYPE
              SYNTAX  INTEGER
              ACCESS  read-only
              STATUS  mandatory
              DESCRIPTION
                      "The upper limit warning value of the sensor times 1000 as integer"
              ::= { s22 9 }

	    s22HiLimitAlarmInt OBJECT-TYPE
              SYNTAX  INTEGER
              ACCESS  read-only
              STATUS  mandatory
              DESCRIPTION
                      "The upper limit alarm value of the sensor times 1000 as integer"
              ::= { s22 10 }

	    s22HysterInt OBJECT-TYPE
              SYNTAX  INTEGER
              ACCESS  read-only
              STATUS  mandatory
              DESCRIPTION
                      "The hysteresis value of the sensor times 1000 as integer"
              ::= { s22 11 }


	-- sensor23:
            s23id OBJECT-TYPE
              SYNTAX  DisplayString
              ACCESS  read-only
              STATUS  mandatory
              DESCRIPTION
                      "A unique value containing sensortype and serial number."
              ::= { s23 1 }

	    s23value OBJECT-TYPE
              SYNTAX  DisplayString
              ACCESS  read-only
              STATUS  mandatory
              DESCRIPTION
                      "The value of the sensor as String."
              ::= { s23 2 }

	    s23unit OBJECT-TYPE
              SYNTAX  DisplayString
              ACCESS  read-only
              STATUS  mandatory
              DESCRIPTION
                      "The unit of the sensor."
              ::= { s23 3 }

	    s23valueInt OBJECT-TYPE
              SYNTAX  INTEGER
              ACCESS  read-write
              STATUS  mandatory
              DESCRIPTION
                      "The value of the sensor times 1000 as integer"
              ::= { s23 4 }

	    s23name OBJECT-TYPE
              SYNTAX  DisplayString
              ACCESS  read-only
              STATUS  mandatory
              DESCRIPTION
                      "The name of the sensor as String. 
		       This name is set by the user in the SNMP Config Table."
              ::= { s23 5 }

	    s23alarmInt OBJECT-TYPE
              SYNTAX  INTEGER
              ACCESS  read-only
              STATUS  mandatory
              DESCRIPTION
                      "The Sensor Alarm Status range 1..5 as integer"
              ::= { s23 6 }

	    s23LoLimitAlarmInt OBJECT-TYPE
              SYNTAX  INTEGER
              ACCESS  read-only
              STATUS  mandatory
              DESCRIPTION
                      "The lower limit alarm value of the sensor times 1000 as integer"
              ::= { s23 7 }

	    s23LoLimitWarnInt OBJECT-TYPE
              SYNTAX  INTEGER
              ACCESS  read-only
              STATUS  mandatory
              DESCRIPTION
                      "The lower limit warning value of the sensor times 1000 as integer"
              ::= { s23 8 }

	    s23HiLimitWarnInt OBJECT-TYPE
              SYNTAX  INTEGER
              ACCESS  read-only
              STATUS  mandatory
              DESCRIPTION
                      "The upper limit warning value of the sensor times 1000 as integer"
              ::= { s23 9 }

	    s23HiLimitAlarmInt OBJECT-TYPE
              SYNTAX  INTEGER
              ACCESS  read-only
              STATUS  mandatory
              DESCRIPTION
                      "The upper limit alarm value of the sensor times 1000 as integer"
              ::= { s23 10 }

	    s23HysterInt OBJECT-TYPE
              SYNTAX  INTEGER
              ACCESS  read-only
              STATUS  mandatory
              DESCRIPTION
                      "The hysteresis value of the sensor times 1000 as integer"
              ::= { s23 11 }


	-- sensor24:
            s24id OBJECT-TYPE
              SYNTAX  DisplayString
              ACCESS  read-only
              STATUS  mandatory
              DESCRIPTION
                      "A unique value containing sensortype and serial number."
              ::= { s24 1 }

	    s24value OBJECT-TYPE
              SYNTAX  DisplayString
              ACCESS  read-only
              STATUS  mandatory
              DESCRIPTION
                      "The value of the sensor as String."
              ::= { s24 2 }

	    s24unit OBJECT-TYPE
              SYNTAX  DisplayString
              ACCESS  read-only
              STATUS  mandatory
              DESCRIPTION
                      "The unit of the sensor."
              ::= { s24 3 }

	    s24valueInt OBJECT-TYPE
              SYNTAX  INTEGER
              ACCESS  read-write
              STATUS  mandatory
              DESCRIPTION
                      "The value of the sensor times 1000 as integer"
              ::= { s24 4 }

	    s24name OBJECT-TYPE
              SYNTAX  DisplayString
              ACCESS  read-only
              STATUS  mandatory
              DESCRIPTION
                      "The name of the sensor as String. 
		       This name is set by the user in the SNMP Config Table."
              ::= { s24 5 }

	    s24alarmInt OBJECT-TYPE
              SYNTAX  INTEGER
              ACCESS  read-only
              STATUS  mandatory
              DESCRIPTION
                      "The Sensor Alarm Status range 1..5 as integer"
              ::= { s24 6 }

	    s24LoLimitAlarmInt OBJECT-TYPE
              SYNTAX  INTEGER
              ACCESS  read-only
              STATUS  mandatory
              DESCRIPTION
                      "The lower limit alarm value of the sensor times 1000 as integer"
              ::= { s24 7 }

	    s24LoLimitWarnInt OBJECT-TYPE
              SYNTAX  INTEGER
              ACCESS  read-only
              STATUS  mandatory
              DESCRIPTION
                      "The lower limit warning value of the sensor times 1000 as integer"
              ::= { s24 8 }

	    s24HiLimitWarnInt OBJECT-TYPE
              SYNTAX  INTEGER
              ACCESS  read-only
              STATUS  mandatory
              DESCRIPTION
                      "The upper limit warning value of the sensor times 1000 as integer"
              ::= { s24 9 }

	    s24HiLimitAlarmInt OBJECT-TYPE
              SYNTAX  INTEGER
              ACCESS  read-only
              STATUS  mandatory
              DESCRIPTION
                      "The upper limit alarm value of the sensor times 1000 as integer"
              ::= { s24 10 }

	    s24HysterInt OBJECT-TYPE
              SYNTAX  INTEGER
              ACCESS  read-only
              STATUS  mandatory
              DESCRIPTION
                      "The hysteresis value of the sensor times 1000 as integer"
              ::= { s24 11 }


	-- sensor25:
            s25id OBJECT-TYPE
              SYNTAX  DisplayString
              ACCESS  read-only
              STATUS  mandatory
              DESCRIPTION
                      "A unique value containing sensortype and serial number."
              ::= { s25 1 }

	    s25value OBJECT-TYPE
              SYNTAX  DisplayString
              ACCESS  read-only
              STATUS  mandatory
              DESCRIPTION
                      "The value of the sensor as String."
              ::= { s25 2 }

	    s25unit OBJECT-TYPE
              SYNTAX  DisplayString
              ACCESS  read-only
              STATUS  mandatory
              DESCRIPTION
                      "The unit of the sensor."
              ::= { s25 3 }

	    s25valueInt OBJECT-TYPE
              SYNTAX  INTEGER
              ACCESS  read-write
              STATUS  mandatory
              DESCRIPTION
                      "The value of the sensor times 1000 as integer"
              ::= { s25 4 }

	    s25name OBJECT-TYPE
              SYNTAX  DisplayString
              ACCESS  read-only
              STATUS  mandatory
              DESCRIPTION
                      "The name of the sensor as String. 
		       This name is set by the user in the SNMP Config Table."
              ::= { s25 5 }

	    s25alarmInt OBJECT-TYPE
              SYNTAX  INTEGER
              ACCESS  read-only
              STATUS  mandatory
              DESCRIPTION
                      "The Sensor Alarm Status range 1..5 as integer"
              ::= { s25 6 }

	    s25LoLimitAlarmInt OBJECT-TYPE
              SYNTAX  INTEGER
              ACCESS  read-only
              STATUS  mandatory
              DESCRIPTION
                      "The lower limit alarm value of the sensor times 1000 as integer"
              ::= { s25 7 }

	    s25LoLimitWarnInt OBJECT-TYPE
              SYNTAX  INTEGER
              ACCESS  read-only
              STATUS  mandatory
              DESCRIPTION
                      "The lower limit warning value of the sensor times 1000 as integer"
              ::= { s25 8 }

	    s25HiLimitWarnInt OBJECT-TYPE
              SYNTAX  INTEGER
              ACCESS  read-only
              STATUS  mandatory
              DESCRIPTION
                      "The upper limit warning value of the sensor times 1000 as integer"
              ::= { s25 9 }

	    s25HiLimitAlarmInt OBJECT-TYPE
              SYNTAX  INTEGER
              ACCESS  read-only
              STATUS  mandatory
              DESCRIPTION
                      "The upper limit alarm value of the sensor times 1000 as integer"
              ::= { s25 10 }

	    s25HysterInt OBJECT-TYPE
              SYNTAX  INTEGER
              ACCESS  read-only
              STATUS  mandatory
              DESCRIPTION
                      "The hysteresis value of the sensor times 1000 as integer"
              ::= { s25 11 }


	-- sensor26:
            s26id OBJECT-TYPE
              SYNTAX  DisplayString
              ACCESS  read-only
              STATUS  mandatory
              DESCRIPTION
                      "A unique value containing sensortype and serial number."
              ::= { s26 1 }

	    s26value OBJECT-TYPE
              SYNTAX  DisplayString
              ACCESS  read-only
              STATUS  mandatory
              DESCRIPTION
                      "The value of the sensor as String."
              ::= { s26 2 }

	    s26unit OBJECT-TYPE
              SYNTAX  DisplayString
              ACCESS  read-only
              STATUS  mandatory
              DESCRIPTION
                      "The unit of the sensor."
              ::= { s26 3 }

	    s26valueInt OBJECT-TYPE
              SYNTAX  INTEGER
              ACCESS  read-write
              STATUS  mandatory
              DESCRIPTION
                      "The value of the sensor times 1000 as integer"
              ::= { s26 4 }

	    s26name OBJECT-TYPE
              SYNTAX  DisplayString
              ACCESS  read-only
              STATUS  mandatory
              DESCRIPTION
                      "The name of the sensor as String. 
		       This name is set by the user in the SNMP Config Table."
              ::= { s26 5 }

	    s26alarmInt OBJECT-TYPE
              SYNTAX  INTEGER
              ACCESS  read-only
              STATUS  mandatory
              DESCRIPTION
                      "The Sensor Alarm Status range 1..5 as integer"
              ::= { s26 6 }

	    s26LoLimitAlarmInt OBJECT-TYPE
              SYNTAX  INTEGER
              ACCESS  read-only
              STATUS  mandatory
              DESCRIPTION
                      "The lower limit alarm value of the sensor times 1000 as integer"
              ::= { s26 7 }

	    s26LoLimitWarnInt OBJECT-TYPE
              SYNTAX  INTEGER
              ACCESS  read-only
              STATUS  mandatory
              DESCRIPTION
                      "The lower limit warning value of the sensor times 1000 as integer"
              ::= { s26 8 }

	    s26HiLimitWarnInt OBJECT-TYPE
              SYNTAX  INTEGER
              ACCESS  read-only
              STATUS  mandatory
              DESCRIPTION
                      "The upper limit warning value of the sensor times 1000 as integer"
              ::= { s26 9 }

	    s26HiLimitAlarmInt OBJECT-TYPE
              SYNTAX  INTEGER
              ACCESS  read-only
              STATUS  mandatory
              DESCRIPTION
                      "The upper limit alarm value of the sensor times 1000 as integer"
              ::= { s26 10 }

	    s26HysterInt OBJECT-TYPE
              SYNTAX  INTEGER
              ACCESS  read-only
              STATUS  mandatory
              DESCRIPTION
                      "The hysteresis value of the sensor times 1000 as integer"
              ::= { s26 11 }


	-- sensor27:
            s27id OBJECT-TYPE
              SYNTAX  DisplayString
              ACCESS  read-only
              STATUS  mandatory
              DESCRIPTION
                      "A unique value containing sensortype and serial number."
              ::= { s27 1 }

	    s27value OBJECT-TYPE
              SYNTAX  DisplayString
              ACCESS  read-only
              STATUS  mandatory
              DESCRIPTION
                      "The value of the sensor as String."
              ::= { s27 2 }

	    s27unit OBJECT-TYPE
              SYNTAX  DisplayString
              ACCESS  read-only
              STATUS  mandatory
              DESCRIPTION
                      "The unit of the sensor."
              ::= { s27 3 }

	    s27valueInt OBJECT-TYPE
              SYNTAX  INTEGER
              ACCESS  read-write
              STATUS  mandatory
              DESCRIPTION
                      "The value of the sensor times 1000 as integer"
              ::= { s27 4 }

	    s27name OBJECT-TYPE
              SYNTAX  DisplayString
              ACCESS  read-only
              STATUS  mandatory
              DESCRIPTION
                      "The name of the sensor as String. 
		       This name is set by the user in the SNMP Config Table."
              ::= { s27 5 }

	    s27alarmInt OBJECT-TYPE
              SYNTAX  INTEGER
              ACCESS  read-only
              STATUS  mandatory
              DESCRIPTION
                      "The Sensor Alarm Status range 1..5 as integer"
              ::= { s27 6 }

	    s27LoLimitAlarmInt OBJECT-TYPE
              SYNTAX  INTEGER
              ACCESS  read-only
              STATUS  mandatory
              DESCRIPTION
                      "The lower limit alarm value of the sensor times 1000 as integer"
              ::= { s27 7 }

	    s27LoLimitWarnInt OBJECT-TYPE
              SYNTAX  INTEGER
              ACCESS  read-only
              STATUS  mandatory
              DESCRIPTION
                      "The lower limit warning value of the sensor times 1000 as integer"
              ::= { s27 8 }

	    s27HiLimitWarnInt OBJECT-TYPE
              SYNTAX  INTEGER
              ACCESS  read-only
              STATUS  mandatory
              DESCRIPTION
                      "The upper limit warning value of the sensor times 1000 as integer"
              ::= { s27 9 }

	    s27HiLimitAlarmInt OBJECT-TYPE
              SYNTAX  INTEGER
              ACCESS  read-only
              STATUS  mandatory
              DESCRIPTION
                      "The upper limit alarm value of the sensor times 1000 as integer"
              ::= { s27 10 }

	    s27HysterInt OBJECT-TYPE
              SYNTAX  INTEGER
              ACCESS  read-only
              STATUS  mandatory
              DESCRIPTION
                      "The hysteresis value of the sensor times 1000 as integer"
              ::= { s27 11 }


	-- sensor28:
            s28id OBJECT-TYPE
              SYNTAX  DisplayString
              ACCESS  read-only
              STATUS  mandatory
              DESCRIPTION
                      "A unique value containing sensortype and serial number."
              ::= { s28 1 }

	    s28value OBJECT-TYPE
              SYNTAX  DisplayString
              ACCESS  read-only
              STATUS  mandatory
              DESCRIPTION
                      "The value of the sensor as String."
              ::= { s28 2 }

	    s28unit OBJECT-TYPE
              SYNTAX  DisplayString
              ACCESS  read-only
              STATUS  mandatory
              DESCRIPTION
                      "The unit of the sensor."
              ::= { s28 3 }

	    s28valueInt OBJECT-TYPE
              SYNTAX  INTEGER
              ACCESS  read-write
              STATUS  mandatory
              DESCRIPTION
                      "The value of the sensor times 1000 as integer"
              ::= { s28 4 }

	    s28name OBJECT-TYPE
              SYNTAX  DisplayString
              ACCESS  read-only
              STATUS  mandatory
              DESCRIPTION
                      "The name of the sensor as String. 
		       This name is set by the user in the SNMP Config Table."
              ::= { s28 5 }

	    s28alarmInt OBJECT-TYPE
              SYNTAX  INTEGER
              ACCESS  read-only
              STATUS  mandatory
              DESCRIPTION
                      "The Sensor Alarm Status range 1..5 as integer"
              ::= { s28 6 }

	    s28LoLimitAlarmInt OBJECT-TYPE
              SYNTAX  INTEGER
              ACCESS  read-only
              STATUS  mandatory
              DESCRIPTION
                      "The lower limit alarm value of the sensor times 1000 as integer"
              ::= { s28 7 }

	    s28LoLimitWarnInt OBJECT-TYPE
              SYNTAX  INTEGER
              ACCESS  read-only
              STATUS  mandatory
              DESCRIPTION
                      "The lower limit warning value of the sensor times 1000 as integer"
              ::= { s28 8 }

	    s28HiLimitWarnInt OBJECT-TYPE
              SYNTAX  INTEGER
              ACCESS  read-only
              STATUS  mandatory
              DESCRIPTION
                      "The upper limit warning value of the sensor times 1000 as integer"
              ::= { s28 9 }

	    s28HiLimitAlarmInt OBJECT-TYPE
              SYNTAX  INTEGER
              ACCESS  read-only
              STATUS  mandatory
              DESCRIPTION
                      "The upper limit alarm value of the sensor times 1000 as integer"
              ::= { s28 10 }

	    s28HysterInt OBJECT-TYPE
              SYNTAX  INTEGER
              ACCESS  read-only
              STATUS  mandatory
              DESCRIPTION
                      "The hysteresis value of the sensor times 1000 as integer"
              ::= { s28 11 }


	-- sensor29:
            s29id OBJECT-TYPE
              SYNTAX  DisplayString
              ACCESS  read-only
              STATUS  mandatory
              DESCRIPTION
                      "A unique value containing sensortype and serial number."
              ::= { s29 1 }

	    s29value OBJECT-TYPE
              SYNTAX  DisplayString
              ACCESS  read-only
              STATUS  mandatory
              DESCRIPTION
                      "The value of the sensor as String."
              ::= { s29 2 }

	    s29unit OBJECT-TYPE
              SYNTAX  DisplayString
              ACCESS  read-only
              STATUS  mandatory
              DESCRIPTION
                      "The unit of the sensor."
              ::= { s29 3 }

	    s29valueInt OBJECT-TYPE
              SYNTAX  INTEGER
              ACCESS  read-write
              STATUS  mandatory
              DESCRIPTION
                      "The value of the sensor times 1000 as integer"
              ::= { s29 4 }

	    s29name OBJECT-TYPE
              SYNTAX  DisplayString
              ACCESS  read-only
              STATUS  mandatory
              DESCRIPTION
                      "The name of the sensor as String. 
		       This name is set by the user in the SNMP Config Table."
              ::= { s29 5 }

	    s29alarmInt OBJECT-TYPE
              SYNTAX  INTEGER
              ACCESS  read-only
              STATUS  mandatory
              DESCRIPTION
                      "The Sensor Alarm Status range 1..5 as integer"
              ::= { s29 6 }

	    s29LoLimitAlarmInt OBJECT-TYPE
              SYNTAX  INTEGER
              ACCESS  read-only
              STATUS  mandatory
              DESCRIPTION
                      "The lower limit alarm value of the sensor times 1000 as integer"
              ::= { s29 7 }

	    s29LoLimitWarnInt OBJECT-TYPE
              SYNTAX  INTEGER
              ACCESS  read-only
              STATUS  mandatory
              DESCRIPTION
                      "The lower limit warning value of the sensor times 1000 as integer"
              ::= { s29 8 }

	    s29HiLimitWarnInt OBJECT-TYPE
              SYNTAX  INTEGER
              ACCESS  read-only
              STATUS  mandatory
              DESCRIPTION
                      "The upper limit warning value of the sensor times 1000 as integer"
              ::= { s29 9 }

	    s29HiLimitAlarmInt OBJECT-TYPE
              SYNTAX  INTEGER
              ACCESS  read-only
              STATUS  mandatory
              DESCRIPTION
                      "The upper limit alarm value of the sensor times 1000 as integer"
              ::= { s29 10 }

	    s29HysterInt OBJECT-TYPE
              SYNTAX  INTEGER
              ACCESS  read-only
              STATUS  mandatory
              DESCRIPTION
                      "The hysteresis value of the sensor times 1000 as integer"
              ::= { s29 11 }


	-- sensor30:
            s30id OBJECT-TYPE
              SYNTAX  DisplayString
              ACCESS  read-only
              STATUS  mandatory
              DESCRIPTION
                      "A unique value containing sensortype and serial number."
              ::= { s30 1 }

	    s30value OBJECT-TYPE
              SYNTAX  DisplayString
              ACCESS  read-only
              STATUS  mandatory
              DESCRIPTION
                      "The value of the sensor as String."
              ::= { s30 2 }

	    s30unit OBJECT-TYPE
              SYNTAX  DisplayString
              ACCESS  read-only
              STATUS  mandatory
              DESCRIPTION
                      "The unit of the sensor."
              ::= { s30 3 }

	    s30valueInt OBJECT-TYPE
              SYNTAX  INTEGER
              ACCESS  read-write
              STATUS  mandatory
              DESCRIPTION
                      "The value of the sensor times 1000 as integer"
              ::= { s30 4 }

	    s30name OBJECT-TYPE
              SYNTAX  DisplayString
              ACCESS  read-only
              STATUS  mandatory
              DESCRIPTION
                      "The name of the sensor as String. 
		       This name is set by the user in the SNMP Config Table."
              ::= { s30 5 }

	    s30alarmInt OBJECT-TYPE
              SYNTAX  INTEGER
              ACCESS  read-only
              STATUS  mandatory
              DESCRIPTION
                      "The Sensor Alarm Status range 1..5 as integer"
              ::= { s30 6 }

	    s30LoLimitAlarmInt OBJECT-TYPE
              SYNTAX  INTEGER
              ACCESS  read-only
              STATUS  mandatory
              DESCRIPTION
                      "The lower limit alarm value of the sensor times 1000 as integer"
              ::= { s30 7 }

	    s30LoLimitWarnInt OBJECT-TYPE
              SYNTAX  INTEGER
              ACCESS  read-only
              STATUS  mandatory
              DESCRIPTION
                      "The lower limit warning value of the sensor times 1000 as integer"
              ::= { s30 8 }

	    s30HiLimitWarnInt OBJECT-TYPE
              SYNTAX  INTEGER
              ACCESS  read-only
              STATUS  mandatory
              DESCRIPTION
                      "The upper limit warning value of the sensor times 1000 as integer"
              ::= { s30 9 }

	    s30HiLimitAlarmInt OBJECT-TYPE
              SYNTAX  INTEGER
              ACCESS  read-only
              STATUS  mandatory
              DESCRIPTION
                      "The upper limit alarm value of the sensor times 1000 as integer"
              ::= { s30 10 }

	    s30HysterInt OBJECT-TYPE
              SYNTAX  INTEGER
              ACCESS  read-only
              STATUS  mandatory
              DESCRIPTION
                      "The hysteresis value of the sensor times 1000 as integer"
              ::= { s30 11 }


  --  31 - 40
	-- sensor31:
            s31id OBJECT-TYPE
              SYNTAX  DisplayString
              ACCESS  read-only
              STATUS  mandatory
              DESCRIPTION
                      "A unique value containing sensortype and serial number."
              ::= { s31 1 }

	    s31value OBJECT-TYPE
              SYNTAX  DisplayString
              ACCESS  read-only
              STATUS  mandatory
              DESCRIPTION
                      "The value of the sensor as String."
              ::= { s31 2 }

	    s31unit OBJECT-TYPE
              SYNTAX  DisplayString
              ACCESS  read-only
              STATUS  mandatory
              DESCRIPTION
                      "The unit of the sensor."
              ::= { s31 3 }

	    s31valueInt OBJECT-TYPE
              SYNTAX  INTEGER
              ACCESS  read-write
              STATUS  mandatory
              DESCRIPTION
                      "The value of the sensor times 1000 as integer"
              ::= { s31 4 }

	    s31name OBJECT-TYPE
              SYNTAX  DisplayString
              ACCESS  read-only
              STATUS  mandatory
              DESCRIPTION
                      "The name of the sensor as String. 
		       This name is set by the user in the SNMP Config Table."
              ::= { s31 5 }

	    s31alarmInt OBJECT-TYPE
              SYNTAX  INTEGER
              ACCESS  read-only
              STATUS  mandatory
              DESCRIPTION
                      "The Sensor Alarm Status range 1..5 as integer"
              ::= { s31 6 }

	    s31LoLimitAlarmInt OBJECT-TYPE
              SYNTAX  INTEGER
              ACCESS  read-only
              STATUS  mandatory
              DESCRIPTION
                      "The lower limit alarm value of the sensor times 1000 as integer"
              ::= { s31 7 }

	    s31LoLimitWarnInt OBJECT-TYPE
              SYNTAX  INTEGER
              ACCESS  read-only
              STATUS  mandatory
              DESCRIPTION
                      "The lower limit warning value of the sensor times 1000 as integer"
              ::= { s31 8 }

	    s31HiLimitWarnInt OBJECT-TYPE
              SYNTAX  INTEGER
              ACCESS  read-only
              STATUS  mandatory
              DESCRIPTION
                      "The upper limit warning value of the sensor times 1000 as integer"
              ::= { s31 9 }

	    s31HiLimitAlarmInt OBJECT-TYPE
              SYNTAX  INTEGER
              ACCESS  read-only
              STATUS  mandatory
              DESCRIPTION
                      "The upper limit alarm value of the sensor times 1000 as integer"
              ::= { s31 10 }

	    s31HysterInt OBJECT-TYPE
              SYNTAX  INTEGER
              ACCESS  read-only
              STATUS  mandatory
              DESCRIPTION
                      "The hysteresis value of the sensor times 1000 as integer"
              ::= { s31 11 }


	-- sensor32:
            s32id OBJECT-TYPE
              SYNTAX  DisplayString
              ACCESS  read-only
              STATUS  mandatory
              DESCRIPTION
                      "A unique value containing sensortype and serial number."
              ::= { s32 1 }

	    s32value OBJECT-TYPE
              SYNTAX  DisplayString
              ACCESS  read-only
              STATUS  mandatory
              DESCRIPTION
                      "The value of the sensor as String."
              ::= { s32 2 }

	    s32unit OBJECT-TYPE
              SYNTAX  DisplayString
              ACCESS  read-only
              STATUS  mandatory
              DESCRIPTION
                      "The unit of the sensor."
              ::= { s32 3 }

	    s32valueInt OBJECT-TYPE
              SYNTAX  INTEGER
              ACCESS  read-write
              STATUS  mandatory
              DESCRIPTION
                      "The value of the sensor times 1000 as integer"
              ::= { s32 4 }

	    s32name OBJECT-TYPE
              SYNTAX  DisplayString
              ACCESS  read-only
              STATUS  mandatory
              DESCRIPTION
                      "The name of the sensor as String. 
		       This name is set by the user in the SNMP Config Table."
              ::= { s32 5 }

	    s32alarmInt OBJECT-TYPE
              SYNTAX  INTEGER
              ACCESS  read-only
              STATUS  mandatory
              DESCRIPTION
                      "The Sensor Alarm Status range 1..5 as integer"
              ::= { s32 6 }

	    s32LoLimitAlarmInt OBJECT-TYPE
              SYNTAX  INTEGER
              ACCESS  read-only
              STATUS  mandatory
              DESCRIPTION
                      "The lower limit alarm value of the sensor times 1000 as integer"
              ::= { s32 7 }

	    s32LoLimitWarnInt OBJECT-TYPE
              SYNTAX  INTEGER
              ACCESS  read-only
              STATUS  mandatory
              DESCRIPTION
                      "The lower limit warning value of the sensor times 1000 as integer"
              ::= { s32 8 }

	    s32HiLimitWarnInt OBJECT-TYPE
              SYNTAX  INTEGER
              ACCESS  read-only
              STATUS  mandatory
              DESCRIPTION
                      "The upper limit warning value of the sensor times 1000 as integer"
              ::= { s32 9 }

	    s32HiLimitAlarmInt OBJECT-TYPE
              SYNTAX  INTEGER
              ACCESS  read-only
              STATUS  mandatory
              DESCRIPTION
                      "The upper limit alarm value of the sensor times 1000 as integer"
              ::= { s32 10 }

	    s32HysterInt OBJECT-TYPE
              SYNTAX  INTEGER
              ACCESS  read-only
              STATUS  mandatory
              DESCRIPTION
                      "The hysteresis value of the sensor times 1000 as integer"
              ::= { s32 11 }


	-- sensor33:
            s33id OBJECT-TYPE
              SYNTAX  DisplayString
              ACCESS  read-only
              STATUS  mandatory
              DESCRIPTION
                      "A unique value containing sensortype and serial number."
              ::= { s33 1 }

	    s33value OBJECT-TYPE
              SYNTAX  DisplayString
              ACCESS  read-only
              STATUS  mandatory
              DESCRIPTION
                      "The value of the sensor as String."
              ::= { s33 2 }

	    s33unit OBJECT-TYPE
              SYNTAX  DisplayString
              ACCESS  read-only
              STATUS  mandatory
              DESCRIPTION
                      "The unit of the sensor."
              ::= { s33 3 }

	    s33valueInt OBJECT-TYPE
              SYNTAX  INTEGER
              ACCESS  read-write
              STATUS  mandatory
              DESCRIPTION
                      "The value of the sensor times 1000 as integer"
              ::= { s33 4 }

	    s33name OBJECT-TYPE
              SYNTAX  DisplayString
              ACCESS  read-only
              STATUS  mandatory
              DESCRIPTION
                      "The name of the sensor as String. 
		       This name is set by the user in the SNMP Config Table."
              ::= { s33 5 }

	    s33alarmInt OBJECT-TYPE
              SYNTAX  INTEGER
              ACCESS  read-only
              STATUS  mandatory
              DESCRIPTION
                      "The Sensor Alarm Status range 1..5 as integer"
              ::= { s33 6 }

	    s33LoLimitAlarmInt OBJECT-TYPE
              SYNTAX  INTEGER
              ACCESS  read-only
              STATUS  mandatory
              DESCRIPTION
                      "The lower limit alarm value of the sensor times 1000 as integer"
              ::= { s33 7 }

	    s33LoLimitWarnInt OBJECT-TYPE
              SYNTAX  INTEGER
              ACCESS  read-only
              STATUS  mandatory
              DESCRIPTION
                      "The lower limit warning value of the sensor times 1000 as integer"
              ::= { s33 8 }

	    s33HiLimitWarnInt OBJECT-TYPE
              SYNTAX  INTEGER
              ACCESS  read-only
              STATUS  mandatory
              DESCRIPTION
                      "The upper limit warning value of the sensor times 1000 as integer"
              ::= { s33 9 }

	    s33HiLimitAlarmInt OBJECT-TYPE
              SYNTAX  INTEGER
              ACCESS  read-only
              STATUS  mandatory
              DESCRIPTION
                      "The upper limit alarm value of the sensor times 1000 as integer"
              ::= { s33 10 }

	    s33HysterInt OBJECT-TYPE
              SYNTAX  INTEGER
              ACCESS  read-only
              STATUS  mandatory
              DESCRIPTION
                      "The hysteresis value of the sensor times 1000 as integer"
              ::= { s33 11 }


	-- sensor34:
            s34id OBJECT-TYPE
              SYNTAX  DisplayString
              ACCESS  read-only
              STATUS  mandatory
              DESCRIPTION
                      "A unique value containing sensortype and serial number."
              ::= { s34 1 }

	    s34value OBJECT-TYPE
              SYNTAX  DisplayString
              ACCESS  read-only
              STATUS  mandatory
              DESCRIPTION
                      "The value of the sensor as String."
              ::= { s34 2 }

	    s34unit OBJECT-TYPE
              SYNTAX  DisplayString
              ACCESS  read-only
              STATUS  mandatory
              DESCRIPTION
                      "The unit of the sensor."
              ::= { s34 3 }

	    s34valueInt OBJECT-TYPE
              SYNTAX  INTEGER
              ACCESS  read-write
              STATUS  mandatory
              DESCRIPTION
                      "The value of the sensor times 1000 as integer"
              ::= { s34 4 }

	    s34name OBJECT-TYPE
              SYNTAX  DisplayString
              ACCESS  read-only
              STATUS  mandatory
              DESCRIPTION
                      "The name of the sensor as String. 
		       This name is set by the user in the SNMP Config Table."
              ::= { s34 5 }

	    s34alarmInt OBJECT-TYPE
              SYNTAX  INTEGER
              ACCESS  read-only
              STATUS  mandatory
              DESCRIPTION
                      "The Sensor Alarm Status range 1..5 as integer"
              ::= { s34 6 }

	    s34LoLimitAlarmInt OBJECT-TYPE
              SYNTAX  INTEGER
              ACCESS  read-only
              STATUS  mandatory
              DESCRIPTION
                      "The lower limit alarm value of the sensor times 1000 as integer"
              ::= { s34 7 }

	    s34LoLimitWarnInt OBJECT-TYPE
              SYNTAX  INTEGER
              ACCESS  read-only
              STATUS  mandatory
              DESCRIPTION
                      "The lower limit warning value of the sensor times 1000 as integer"
              ::= { s34 8 }

	    s34HiLimitWarnInt OBJECT-TYPE
              SYNTAX  INTEGER
              ACCESS  read-only
              STATUS  mandatory
              DESCRIPTION
                      "The upper limit warning value of the sensor times 1000 as integer"
              ::= { s34 9 }

	    s34HiLimitAlarmInt OBJECT-TYPE
              SYNTAX  INTEGER
              ACCESS  read-only
              STATUS  mandatory
              DESCRIPTION
                      "The upper limit alarm value of the sensor times 1000 as integer"
              ::= { s34 10 }

	    s34HysterInt OBJECT-TYPE
              SYNTAX  INTEGER
              ACCESS  read-only
              STATUS  mandatory
              DESCRIPTION
                      "The hysteresis value of the sensor times 1000 as integer"
              ::= { s34 11 }


	-- sensor35:
            s35id OBJECT-TYPE
              SYNTAX  DisplayString
              ACCESS  read-only
              STATUS  mandatory
              DESCRIPTION
                      "A unique value containing sensortype and serial number."
              ::= { s35 1 }

	    s35value OBJECT-TYPE
              SYNTAX  DisplayString
              ACCESS  read-only
              STATUS  mandatory
              DESCRIPTION
                      "The value of the sensor as String."
              ::= { s35 2 }

	    s35unit OBJECT-TYPE
              SYNTAX  DisplayString
              ACCESS  read-only
              STATUS  mandatory
              DESCRIPTION
                      "The unit of the sensor."
              ::= { s35 3 }

	    s35valueInt OBJECT-TYPE
              SYNTAX  INTEGER
              ACCESS  read-write
              STATUS  mandatory
              DESCRIPTION
                      "The value of the sensor times 1000 as integer"
              ::= { s35 4 }

	    s35name OBJECT-TYPE
              SYNTAX  DisplayString
              ACCESS  read-only
              STATUS  mandatory
              DESCRIPTION
                      "The name of the sensor as String. 
		       This name is set by the user in the SNMP Config Table."
              ::= { s35 5 }

	    s35alarmInt OBJECT-TYPE
              SYNTAX  INTEGER
              ACCESS  read-only
              STATUS  mandatory
              DESCRIPTION
                      "The Sensor Alarm Status range 1..5 as integer"
              ::= { s35 6 }

	    s35LoLimitAlarmInt OBJECT-TYPE
              SYNTAX  INTEGER
              ACCESS  read-only
              STATUS  mandatory
              DESCRIPTION
                      "The lower limit alarm value of the sensor times 1000 as integer"
              ::= { s35 7 }

	    s35LoLimitWarnInt OBJECT-TYPE
              SYNTAX  INTEGER
              ACCESS  read-only
              STATUS  mandatory
              DESCRIPTION
                      "The lower limit warning value of the sensor times 1000 as integer"
              ::= { s35 8 }

	    s35HiLimitWarnInt OBJECT-TYPE
              SYNTAX  INTEGER
              ACCESS  read-only
              STATUS  mandatory
              DESCRIPTION
                      "The upper limit warning value of the sensor times 1000 as integer"
              ::= { s35 9 }

	    s35HiLimitAlarmInt OBJECT-TYPE
              SYNTAX  INTEGER
              ACCESS  read-only
              STATUS  mandatory
              DESCRIPTION
                      "The upper limit alarm value of the sensor times 1000 as integer"
              ::= { s35 10 }

	    s35HysterInt OBJECT-TYPE
              SYNTAX  INTEGER
              ACCESS  read-only
              STATUS  mandatory
              DESCRIPTION
                      "The hysteresis value of the sensor times 1000 as integer"
              ::= { s35 11 }



	-- sensor36:
            s36id OBJECT-TYPE
              SYNTAX  DisplayString
              ACCESS  read-only
              STATUS  mandatory
              DESCRIPTION
                      "A unique value containing sensortype and serial number."
              ::= { s36 1 }

	    s36value OBJECT-TYPE
              SYNTAX  DisplayString
              ACCESS  read-only
              STATUS  mandatory
              DESCRIPTION
                      "The value of the sensor as String."
              ::= { s36 2 }

	    s36unit OBJECT-TYPE
              SYNTAX  DisplayString
              ACCESS  read-only
              STATUS  mandatory
              DESCRIPTION
                      "The unit of the sensor."
              ::= { s36 3 }

	    s36valueInt OBJECT-TYPE
              SYNTAX  INTEGER
              ACCESS  read-write
              STATUS  mandatory
              DESCRIPTION
                      "The value of the sensor times 1000 as integer"
              ::= { s36 4 }

	    s36name OBJECT-TYPE
              SYNTAX  DisplayString
              ACCESS  read-only
              STATUS  mandatory
              DESCRIPTION
                      "The name of the sensor as String. 
		       This name is set by the user in the SNMP Config Table."
              ::= { s36 5 }

	    s36alarmInt OBJECT-TYPE
              SYNTAX  INTEGER
              ACCESS  read-only
              STATUS  mandatory
              DESCRIPTION
                      "The Sensor Alarm Status range 1..5 as integer"
              ::= { s36 6 }

	    s36LoLimitAlarmInt OBJECT-TYPE
              SYNTAX  INTEGER
              ACCESS  read-only
              STATUS  mandatory
              DESCRIPTION
                      "The lower limit alarm value of the sensor times 1000 as integer"
              ::= { s36 7 }

	    s36LoLimitWarnInt OBJECT-TYPE
              SYNTAX  INTEGER
              ACCESS  read-only
              STATUS  mandatory
              DESCRIPTION
                      "The lower limit warning value of the sensor times 1000 as integer"
              ::= { s36 8 }

	    s36HiLimitWarnInt OBJECT-TYPE
              SYNTAX  INTEGER
              ACCESS  read-only
              STATUS  mandatory
              DESCRIPTION
                      "The upper limit warning value of the sensor times 1000 as integer"
              ::= { s36 9 }

	    s36HiLimitAlarmInt OBJECT-TYPE
              SYNTAX  INTEGER
              ACCESS  read-only
              STATUS  mandatory
              DESCRIPTION
                      "The upper limit alarm value of the sensor times 1000 as integer"
              ::= { s36 10 }

	    s36HysterInt OBJECT-TYPE
              SYNTAX  INTEGER
              ACCESS  read-only
              STATUS  mandatory
              DESCRIPTION
                      "The hysteresis value of the sensor times 1000 as integer"
              ::= { s36 11 }


	-- sensor37:
            s37id OBJECT-TYPE
              SYNTAX  DisplayString
              ACCESS  read-only
              STATUS  mandatory
              DESCRIPTION
                      "A unique value containing sensortype and serial number."
              ::= { s37 1 }

	    s37value OBJECT-TYPE
              SYNTAX  DisplayString
              ACCESS  read-only
              STATUS  mandatory
              DESCRIPTION
                      "The value of the sensor as String."
              ::= { s37 2 }

	    s37unit OBJECT-TYPE
              SYNTAX  DisplayString
              ACCESS  read-only
              STATUS  mandatory
              DESCRIPTION
                      "The unit of the sensor."
              ::= { s37 3 }

	    s37valueInt OBJECT-TYPE
              SYNTAX  INTEGER
              ACCESS  read-write
              STATUS  mandatory
              DESCRIPTION
                      "The value of the sensor times 1000 as integer"
              ::= { s37 4 }

	    s37name OBJECT-TYPE
              SYNTAX  DisplayString
              ACCESS  read-only
              STATUS  mandatory
              DESCRIPTION
                      "The name of the sensor as String. 
		       This name is set by the user in the SNMP Config Table."
              ::= { s37 5 }

	    s37alarmInt OBJECT-TYPE
              SYNTAX  INTEGER
              ACCESS  read-only
              STATUS  mandatory
              DESCRIPTION
                      "The Sensor Alarm Status range 1..5 as integer"
              ::= { s37 6 }

	    s37LoLimitAlarmInt OBJECT-TYPE
              SYNTAX  INTEGER
              ACCESS  read-only
              STATUS  mandatory
              DESCRIPTION
                      "The lower limit alarm value of the sensor times 1000 as integer"
              ::= { s37 7 }

	    s37LoLimitWarnInt OBJECT-TYPE
              SYNTAX  INTEGER
              ACCESS  read-only
              STATUS  mandatory
              DESCRIPTION
                      "The lower limit warning value of the sensor times 1000 as integer"
              ::= { s37 8 }

	    s37HiLimitWarnInt OBJECT-TYPE
              SYNTAX  INTEGER
              ACCESS  read-only
              STATUS  mandatory
              DESCRIPTION
                      "The upper limit warning value of the sensor times 1000 as integer"
              ::= { s37 9 }

	    s37HiLimitAlarmInt OBJECT-TYPE
              SYNTAX  INTEGER
              ACCESS  read-only
              STATUS  mandatory
              DESCRIPTION
                      "The upper limit alarm value of the sensor times 1000 as integer"
              ::= { s37 10 }

	    s37HysterInt OBJECT-TYPE
              SYNTAX  INTEGER
              ACCESS  read-only
              STATUS  mandatory
              DESCRIPTION
                      "The hysteresis value of the sensor times 1000 as integer"
              ::= { s37 11 }


	-- sensor38:
            s38id OBJECT-TYPE
              SYNTAX  DisplayString
              ACCESS  read-only
              STATUS  mandatory
              DESCRIPTION
                      "A unique value containing sensortype and serial number."
              ::= { s38 1 }

	    s38value OBJECT-TYPE
              SYNTAX  DisplayString
              ACCESS  read-only
              STATUS  mandatory
              DESCRIPTION
                      "The value of the sensor as String."
              ::= { s38 2 }

	    s38unit OBJECT-TYPE
              SYNTAX  DisplayString
              ACCESS  read-only
              STATUS  mandatory
              DESCRIPTION
                      "The unit of the sensor."
              ::= { s38 3 }

	    s38valueInt OBJECT-TYPE
              SYNTAX  INTEGER
              ACCESS  read-write
              STATUS  mandatory
              DESCRIPTION
                      "The value of the sensor times 1000 as integer"
              ::= { s38 4 }

	    s38name OBJECT-TYPE
              SYNTAX  DisplayString
              ACCESS  read-only
              STATUS  mandatory
              DESCRIPTION
                      "The name of the sensor as String. 
		       This name is set by the user in the SNMP Config Table."
              ::= { s38 5 }

	    s38alarmInt OBJECT-TYPE
              SYNTAX  INTEGER
              ACCESS  read-only
              STATUS  mandatory
              DESCRIPTION
                      "The Sensor Alarm Status range 1..5 as integer"
              ::= { s38 6 }

	    s38LoLimitAlarmInt OBJECT-TYPE
              SYNTAX  INTEGER
              ACCESS  read-only
              STATUS  mandatory
              DESCRIPTION
                      "The lower limit alarm value of the sensor times 1000 as integer"
              ::= { s38 7 }

	    s38LoLimitWarnInt OBJECT-TYPE
              SYNTAX  INTEGER
              ACCESS  read-only
              STATUS  mandatory
              DESCRIPTION
                      "The lower limit warning value of the sensor times 1000 as integer"
              ::= { s38 8 }

	    s38HiLimitWarnInt OBJECT-TYPE
              SYNTAX  INTEGER
              ACCESS  read-only
              STATUS  mandatory
              DESCRIPTION
                      "The upper limit warning value of the sensor times 1000 as integer"
              ::= { s38 9 }

	    s38HiLimitAlarmInt OBJECT-TYPE
              SYNTAX  INTEGER
              ACCESS  read-only
              STATUS  mandatory
              DESCRIPTION
                      "The upper limit alarm value of the sensor times 1000 as integer"
              ::= { s38 10 }

	    s38HysterInt OBJECT-TYPE
              SYNTAX  INTEGER
              ACCESS  read-only
              STATUS  mandatory
              DESCRIPTION
                      "The hysteresis value of the sensor times 1000 as integer"
              ::= { s38 11 }


	-- sensor39:
            s39id OBJECT-TYPE
              SYNTAX  DisplayString
              ACCESS  read-only
              STATUS  mandatory
              DESCRIPTION
                      "A unique value containing sensortype and serial number."
              ::= { s39 1 }

	    s39value OBJECT-TYPE
              SYNTAX  DisplayString
              ACCESS  read-only
              STATUS  mandatory
              DESCRIPTION
                      "The value of the sensor as String."
              ::= { s39 2 }

	    s39unit OBJECT-TYPE
              SYNTAX  DisplayString
              ACCESS  read-only
              STATUS  mandatory
              DESCRIPTION
                      "The unit of the sensor."
              ::= { s39 3 }

	    s39valueInt OBJECT-TYPE
              SYNTAX  INTEGER
              ACCESS  read-write
              STATUS  mandatory
              DESCRIPTION
                      "The value of the sensor times 1000 as integer"
              ::= { s39 4 }

	    s39name OBJECT-TYPE
              SYNTAX  DisplayString
              ACCESS  read-only
              STATUS  mandatory
              DESCRIPTION
                      "The name of the sensor as String. 
		       This name is set by the user in the SNMP Config Table."
              ::= { s39 5 }

	    s39alarmInt OBJECT-TYPE
              SYNTAX  INTEGER
              ACCESS  read-only
              STATUS  mandatory
              DESCRIPTION
                      "The Sensor Alarm Status range 1..5 as integer"
              ::= { s39 6 }

	    s39LoLimitAlarmInt OBJECT-TYPE
              SYNTAX  INTEGER
              ACCESS  read-only
              STATUS  mandatory
              DESCRIPTION
                      "The lower limit alarm value of the sensor times 1000 as integer"
              ::= { s39 7 }

	    s39LoLimitWarnInt OBJECT-TYPE
              SYNTAX  INTEGER
              ACCESS  read-only
              STATUS  mandatory
              DESCRIPTION
                      "The lower limit warning value of the sensor times 1000 as integer"
              ::= { s39 8 }

	    s39HiLimitWarnInt OBJECT-TYPE
              SYNTAX  INTEGER
              ACCESS  read-only
              STATUS  mandatory
              DESCRIPTION
                      "The upper limit warning value of the sensor times 1000 as integer"
              ::= { s39 9 }

	    s39HiLimitAlarmInt OBJECT-TYPE
              SYNTAX  INTEGER
              ACCESS  read-only
              STATUS  mandatory
              DESCRIPTION
                      "The upper limit alarm value of the sensor times 1000 as integer"
              ::= { s39 10 }

	    s39HysterInt OBJECT-TYPE
              SYNTAX  INTEGER
              ACCESS  read-only
              STATUS  mandatory
              DESCRIPTION
                      "The hysteresis value of the sensor times 1000 as integer"
              ::= { s39 11 }


	-- sensor40:
            s40id OBJECT-TYPE
              SYNTAX  DisplayString
              ACCESS  read-only
              STATUS  mandatory
              DESCRIPTION
                      "A unique value containing sensortype and serial number."
              ::= { s40 1 }

	    s40value OBJECT-TYPE
              SYNTAX  DisplayString
              ACCESS  read-only
              STATUS  mandatory
              DESCRIPTION
                      "The value of the sensor as String."
              ::= { s40 2 }

	    s40unit OBJECT-TYPE
              SYNTAX  DisplayString
              ACCESS  read-only
              STATUS  mandatory
              DESCRIPTION
                      "The unit of the sensor."
              ::= { s40 3 }

	    s40valueInt OBJECT-TYPE
              SYNTAX  INTEGER
              ACCESS  read-write
              STATUS  mandatory
              DESCRIPTION
                      "The value of the sensor times 1000 as integer"
              ::= { s40 4 }

	    s40name OBJECT-TYPE
              SYNTAX  DisplayString
              ACCESS  read-only
              STATUS  mandatory
              DESCRIPTION
                      "The name of the sensor as String. 
		       This name is set by the user in the SNMP Config Table."
              ::= { s40 5 }

	    s40alarmInt OBJECT-TYPE
              SYNTAX  INTEGER
              ACCESS  read-only
              STATUS  mandatory
              DESCRIPTION
                      "The Sensor Alarm Status range 1..5 as integer"
              ::= { s40 6 }

	    s40LoLimitAlarmInt OBJECT-TYPE
              SYNTAX  INTEGER
              ACCESS  read-only
              STATUS  mandatory
              DESCRIPTION
                      "The lower limit alarm value of the sensor times 1000 as integer"
              ::= { s40 7 }

	    s40LoLimitWarnInt OBJECT-TYPE
              SYNTAX  INTEGER
              ACCESS  read-only
              STATUS  mandatory
              DESCRIPTION
                      "The lower limit warning value of the sensor times 1000 as integer"
              ::= { s40 8 }

	    s40HiLimitWarnInt OBJECT-TYPE
              SYNTAX  INTEGER
              ACCESS  read-only
              STATUS  mandatory
              DESCRIPTION
                      "The upper limit warning value of the sensor times 1000 as integer"
              ::= { s40 9 }

	    s40HiLimitAlarmInt OBJECT-TYPE
              SYNTAX  INTEGER
              ACCESS  read-only
              STATUS  mandatory
              DESCRIPTION
                      "The upper limit alarm value of the sensor times 1000 as integer"
              ::= { s40 10 }

	    s40HysterInt OBJECT-TYPE
              SYNTAX  INTEGER
              ACCESS  read-only
              STATUS  mandatory
              DESCRIPTION
                      "The hysteresis value of the sensor times 1000 as integer"
              ::= { s40 11 }


  --  41 - 50
	-- sensor41:
            s41id OBJECT-TYPE
              SYNTAX  DisplayString
              ACCESS  read-only
              STATUS  mandatory
              DESCRIPTION
                      "A unique value containing sensortype and serial number."
              ::= { s41 1 }

	    s41value OBJECT-TYPE
              SYNTAX  DisplayString
              ACCESS  read-only
              STATUS  mandatory
              DESCRIPTION
                      "The value of the sensor as String."
              ::= { s41 2 }

	    s41unit OBJECT-TYPE
              SYNTAX  DisplayString
              ACCESS  read-only
              STATUS  mandatory
              DESCRIPTION
                      "The unit of the sensor."
              ::= { s41 3 }

	    s41valueInt OBJECT-TYPE
              SYNTAX  INTEGER
              ACCESS  read-write
              STATUS  mandatory
              DESCRIPTION
                      "The value of the sensor times 1000 as integer"
              ::= { s41 4 }

	    s41name OBJECT-TYPE
              SYNTAX  DisplayString
              ACCESS  read-only
              STATUS  mandatory
              DESCRIPTION
                      "The name of the sensor as String. 
		       This name is set by the user in the SNMP Config Table."
              ::= { s41 5 }

	    s41alarmInt OBJECT-TYPE
              SYNTAX  INTEGER
              ACCESS  read-only
              STATUS  mandatory
              DESCRIPTION
                      "The Sensor Alarm Status range 1..5 as integer"
              ::= { s41 6 }

	    s41LoLimitAlarmInt OBJECT-TYPE
              SYNTAX  INTEGER
              ACCESS  read-only
              STATUS  mandatory
              DESCRIPTION
                      "The lower limit alarm value of the sensor times 1000 as integer"
              ::= { s41 7 }

	    s41LoLimitWarnInt OBJECT-TYPE
              SYNTAX  INTEGER
              ACCESS  read-only
              STATUS  mandatory
              DESCRIPTION
                      "The lower limit warning value of the sensor times 1000 as integer"
              ::= { s41 8 }

	    s41HiLimitWarnInt OBJECT-TYPE
              SYNTAX  INTEGER
              ACCESS  read-only
              STATUS  mandatory
              DESCRIPTION
                      "The upper limit warning value of the sensor times 1000 as integer"
              ::= { s41 9 }

	    s41HiLimitAlarmInt OBJECT-TYPE
              SYNTAX  INTEGER
              ACCESS  read-only
              STATUS  mandatory
              DESCRIPTION
                      "The upper limit alarm value of the sensor times 1000 as integer"
              ::= { s41 10 }

	    s41HysterInt OBJECT-TYPE
              SYNTAX  INTEGER
              ACCESS  read-only
              STATUS  mandatory
              DESCRIPTION
                      "The hysteresis value of the sensor times 1000 as integer"
              ::= { s41 11 }


	-- sensor42:
            s42id OBJECT-TYPE
              SYNTAX  DisplayString
              ACCESS  read-only
              STATUS  mandatory
              DESCRIPTION
                      "A unique value containing sensortype and serial number."
              ::= { s42 1 }

	    s42value OBJECT-TYPE
              SYNTAX  DisplayString
              ACCESS  read-only
              STATUS  mandatory
              DESCRIPTION
                      "The value of the sensor as String."
              ::= { s42 2 }

	    s42unit OBJECT-TYPE
              SYNTAX  DisplayString
              ACCESS  read-only
              STATUS  mandatory
              DESCRIPTION
                      "The unit of the sensor."
              ::= { s42 3 }

	    s42valueInt OBJECT-TYPE
              SYNTAX  INTEGER
              ACCESS  read-write
              STATUS  mandatory
              DESCRIPTION
                      "The value of the sensor times 1000 as integer"
              ::= { s42 4 }

	    s42name OBJECT-TYPE
              SYNTAX  DisplayString
              ACCESS  read-only
              STATUS  mandatory
              DESCRIPTION
                      "The name of the sensor as String. 
		       This name is set by the user in the SNMP Config Table."
              ::= { s42 5 }

	    s42alarmInt OBJECT-TYPE
              SYNTAX  INTEGER
              ACCESS  read-only
              STATUS  mandatory
              DESCRIPTION
                      "The Sensor Alarm Status range 1..5 as integer"
              ::= { s42 6 }

	    s42LoLimitAlarmInt OBJECT-TYPE
              SYNTAX  INTEGER
              ACCESS  read-only
              STATUS  mandatory
              DESCRIPTION
                      "The lower limit alarm value of the sensor times 1000 as integer"
              ::= { s42 7 }

	    s42LoLimitWarnInt OBJECT-TYPE
              SYNTAX  INTEGER
              ACCESS  read-only
              STATUS  mandatory
              DESCRIPTION
                      "The lower limit warning value of the sensor times 1000 as integer"
              ::= { s42 8 }

	    s42HiLimitWarnInt OBJECT-TYPE
              SYNTAX  INTEGER
              ACCESS  read-only
              STATUS  mandatory
              DESCRIPTION
                      "The upper limit warning value of the sensor times 1000 as integer"
              ::= { s42 9 }

	    s42HiLimitAlarmInt OBJECT-TYPE
              SYNTAX  INTEGER
              ACCESS  read-only
              STATUS  mandatory
              DESCRIPTION
                      "The upper limit alarm value of the sensor times 1000 as integer"
              ::= { s42 10 }

	    s42HysterInt OBJECT-TYPE
              SYNTAX  INTEGER
              ACCESS  read-only
              STATUS  mandatory
              DESCRIPTION
                      "The hysteresis value of the sensor times 1000 as integer"
              ::= { s42 11 }


	-- sensor43:
            s43id OBJECT-TYPE
              SYNTAX  DisplayString
              ACCESS  read-only
              STATUS  mandatory
              DESCRIPTION
                      "A unique value containing sensortype and serial number."
              ::= { s43 1 }

	    s43value OBJECT-TYPE
              SYNTAX  DisplayString
              ACCESS  read-only
              STATUS  mandatory
              DESCRIPTION
                      "The value of the sensor as String."
              ::= { s43 2 }

	    s43unit OBJECT-TYPE
              SYNTAX  DisplayString
              ACCESS  read-only
              STATUS  mandatory
              DESCRIPTION
                      "The unit of the sensor."
              ::= { s43 3 }

	    s43valueInt OBJECT-TYPE
              SYNTAX  INTEGER
              ACCESS  read-write
              STATUS  mandatory
              DESCRIPTION
                      "The value of the sensor times 1000 as integer"
              ::= { s43 4 }

	    s43name OBJECT-TYPE
              SYNTAX  DisplayString
              ACCESS  read-only
              STATUS  mandatory
              DESCRIPTION
                      "The name of the sensor as String. 
		       This name is set by the user in the SNMP Config Table."
              ::= { s43 5 }

	    s43alarmInt OBJECT-TYPE
              SYNTAX  INTEGER
              ACCESS  read-only
              STATUS  mandatory
              DESCRIPTION
                      "The Sensor Alarm Status range 1..5 as integer"
              ::= { s43 6 }

	    s43LoLimitAlarmInt OBJECT-TYPE
              SYNTAX  INTEGER
              ACCESS  read-only
              STATUS  mandatory
              DESCRIPTION
                      "The lower limit alarm value of the sensor times 1000 as integer"
              ::= { s43 7 }

	    s43LoLimitWarnInt OBJECT-TYPE
              SYNTAX  INTEGER
              ACCESS  read-only
              STATUS  mandatory
              DESCRIPTION
                      "The lower limit warning value of the sensor times 1000 as integer"
              ::= { s43 8 }

	    s43HiLimitWarnInt OBJECT-TYPE
              SYNTAX  INTEGER
              ACCESS  read-only
              STATUS  mandatory
              DESCRIPTION
                      "The upper limit warning value of the sensor times 1000 as integer"
              ::= { s43 9 }

	    s43HiLimitAlarmInt OBJECT-TYPE
              SYNTAX  INTEGER
              ACCESS  read-only
              STATUS  mandatory
              DESCRIPTION
                      "The upper limit alarm value of the sensor times 1000 as integer"
              ::= { s43 10 }

	    s43HysterInt OBJECT-TYPE
              SYNTAX  INTEGER
              ACCESS  read-only
              STATUS  mandatory
              DESCRIPTION
                      "The hysteresis value of the sensor times 1000 as integer"
              ::= { s43 11 }


	-- sensor44:
            s44id OBJECT-TYPE
              SYNTAX  DisplayString
              ACCESS  read-only
              STATUS  mandatory
              DESCRIPTION
                      "A unique value containing sensortype and serial number."
              ::= { s44 1 }

	    s44value OBJECT-TYPE
              SYNTAX  DisplayString
              ACCESS  read-only
              STATUS  mandatory
              DESCRIPTION
                      "The value of the sensor as String."
              ::= { s44 2 }

	    s44unit OBJECT-TYPE
              SYNTAX  DisplayString
              ACCESS  read-only
              STATUS  mandatory
              DESCRIPTION
                      "The unit of the sensor."
              ::= { s44 3 }

	    s44valueInt OBJECT-TYPE
              SYNTAX  INTEGER
              ACCESS  read-write
              STATUS  mandatory
              DESCRIPTION
                      "The value of the sensor times 1000 as integer"
              ::= { s44 4 }

	    s44name OBJECT-TYPE
              SYNTAX  DisplayString
              ACCESS  read-only
              STATUS  mandatory
              DESCRIPTION
                      "The name of the sensor as String. 
		       This name is set by the user in the SNMP Config Table."
              ::= { s44 5 }

	    s44alarmInt OBJECT-TYPE
              SYNTAX  INTEGER
              ACCESS  read-only
              STATUS  mandatory
              DESCRIPTION
                      "The Sensor Alarm Status range 1..5 as integer"
              ::= { s44 6 }

	    s44LoLimitAlarmInt OBJECT-TYPE
              SYNTAX  INTEGER
              ACCESS  read-only
              STATUS  mandatory
              DESCRIPTION
                      "The lower limit alarm value of the sensor times 1000 as integer"
              ::= { s44 7 }

	    s44LoLimitWarnInt OBJECT-TYPE
              SYNTAX  INTEGER
              ACCESS  read-only
              STATUS  mandatory
              DESCRIPTION
                      "The lower limit warning value of the sensor times 1000 as integer"
              ::= { s44 8 }

	    s44HiLimitWarnInt OBJECT-TYPE
              SYNTAX  INTEGER
              ACCESS  read-only
              STATUS  mandatory
              DESCRIPTION
                      "The upper limit warning value of the sensor times 1000 as integer"
              ::= { s44 9 }

	    s44HiLimitAlarmInt OBJECT-TYPE
              SYNTAX  INTEGER
              ACCESS  read-only
              STATUS  mandatory
              DESCRIPTION
                      "The upper limit alarm value of the sensor times 1000 as integer"
              ::= { s44 10 }

	    s44HysterInt OBJECT-TYPE
              SYNTAX  INTEGER
              ACCESS  read-only
              STATUS  mandatory
              DESCRIPTION
                      "The hysteresis value of the sensor times 1000 as integer"
              ::= { s44 11 }


	-- sensor45:
            s45id OBJECT-TYPE
              SYNTAX  DisplayString
              ACCESS  read-only
              STATUS  mandatory
              DESCRIPTION
                      "A unique value containing sensortype and serial number."
              ::= { s45 1 }

	    s45value OBJECT-TYPE
              SYNTAX  DisplayString
              ACCESS  read-only
              STATUS  mandatory
              DESCRIPTION
                      "The value of the sensor as String."
              ::= { s45 2 }

	    s45unit OBJECT-TYPE
              SYNTAX  DisplayString
              ACCESS  read-only
              STATUS  mandatory
              DESCRIPTION
                      "The unit of the sensor."
              ::= { s45 3 }

	    s45valueInt OBJECT-TYPE
              SYNTAX  INTEGER
              ACCESS  read-write
              STATUS  mandatory
              DESCRIPTION
                      "The value of the sensor times 1000 as integer"
              ::= { s45 4 }

	    s45name OBJECT-TYPE
              SYNTAX  DisplayString
              ACCESS  read-only
              STATUS  mandatory
              DESCRIPTION
                      "The name of the sensor as String. 
		       This name is set by the user in the SNMP Config Table."
              ::= { s45 5 }

	    s45alarmInt OBJECT-TYPE
              SYNTAX  INTEGER
              ACCESS  read-only
              STATUS  mandatory
              DESCRIPTION
                      "The Sensor Alarm Status range 1..5 as integer"
              ::= { s45 6 }

	    s45LoLimitAlarmInt OBJECT-TYPE
              SYNTAX  INTEGER
              ACCESS  read-only
              STATUS  mandatory
              DESCRIPTION
                      "The lower limit alarm value of the sensor times 1000 as integer"
              ::= { s45 7 }

	    s45LoLimitWarnInt OBJECT-TYPE
              SYNTAX  INTEGER
              ACCESS  read-only
              STATUS  mandatory
              DESCRIPTION
                      "The lower limit warning value of the sensor times 1000 as integer"
              ::= { s45 8 }

	    s45HiLimitWarnInt OBJECT-TYPE
              SYNTAX  INTEGER
              ACCESS  read-only
              STATUS  mandatory
              DESCRIPTION
                      "The upper limit warning value of the sensor times 1000 as integer"
              ::= { s45 9 }

	    s45HiLimitAlarmInt OBJECT-TYPE
              SYNTAX  INTEGER
              ACCESS  read-only
              STATUS  mandatory
              DESCRIPTION
                      "The upper limit alarm value of the sensor times 1000 as integer"
              ::= { s45 10 }

	    s45HysterInt OBJECT-TYPE
              SYNTAX  INTEGER
              ACCESS  read-only
              STATUS  mandatory
              DESCRIPTION
                      "The hysteresis value of the sensor times 1000 as integer"
              ::= { s45 11 }


	-- sensor46:
            s46id OBJECT-TYPE
              SYNTAX  DisplayString
              ACCESS  read-only
              STATUS  mandatory
              DESCRIPTION
                      "A unique value containing sensortype and serial number."
              ::= { s46 1 }

	    s46value OBJECT-TYPE
              SYNTAX  DisplayString
              ACCESS  read-only
              STATUS  mandatory
              DESCRIPTION
                      "The value of the sensor as String."
              ::= { s46 2 }

	    s46unit OBJECT-TYPE
              SYNTAX  DisplayString
              ACCESS  read-only
              STATUS  mandatory
              DESCRIPTION
                      "The unit of the sensor."
              ::= { s46 3 }

	    s46valueInt OBJECT-TYPE
              SYNTAX  INTEGER
              ACCESS  read-write
              STATUS  mandatory
              DESCRIPTION
                      "The value of the sensor times 1000 as integer"
              ::= { s46 4 }

	    s46name OBJECT-TYPE
              SYNTAX  DisplayString
              ACCESS  read-only
              STATUS  mandatory
              DESCRIPTION
                      "The name of the sensor as String. 
		       This name is set by the user in the SNMP Config Table."
              ::= { s46 5 }

	    s46alarmInt OBJECT-TYPE
              SYNTAX  INTEGER
              ACCESS  read-only
              STATUS  mandatory
              DESCRIPTION
                      "The Sensor Alarm Status range 1..5 as integer"
              ::= { s46 6 }

	    s46LoLimitAlarmInt OBJECT-TYPE
              SYNTAX  INTEGER
              ACCESS  read-only
              STATUS  mandatory
              DESCRIPTION
                      "The lower limit alarm value of the sensor times 1000 as integer"
              ::= { s46 7 }

	    s46LoLimitWarnInt OBJECT-TYPE
              SYNTAX  INTEGER
              ACCESS  read-only
              STATUS  mandatory
              DESCRIPTION
                      "The lower limit warning value of the sensor times 1000 as integer"
              ::= { s46 8 }

	    s46HiLimitWarnInt OBJECT-TYPE
              SYNTAX  INTEGER
              ACCESS  read-only
              STATUS  mandatory
              DESCRIPTION
                      "The upper limit warning value of the sensor times 1000 as integer"
              ::= { s46 9 }

	    s46HiLimitAlarmInt OBJECT-TYPE
              SYNTAX  INTEGER
              ACCESS  read-only
              STATUS  mandatory
              DESCRIPTION
                      "The upper limit alarm value of the sensor times 1000 as integer"
              ::= { s46 10 }

	    s46HysterInt OBJECT-TYPE
              SYNTAX  INTEGER
              ACCESS  read-only
              STATUS  mandatory
              DESCRIPTION
                      "The hysteresis value of the sensor times 1000 as integer"
              ::= { s46 11 }


	-- sensor47:
            s47id OBJECT-TYPE
              SYNTAX  DisplayString
              ACCESS  read-only
              STATUS  mandatory
              DESCRIPTION
                      "A unique value containing sensortype and serial number."
              ::= { s47 1 }

	    s47value OBJECT-TYPE
              SYNTAX  DisplayString
              ACCESS  read-only
              STATUS  mandatory
              DESCRIPTION
                      "The value of the sensor as String."
              ::= { s47 2 }

	    s47unit OBJECT-TYPE
              SYNTAX  DisplayString
              ACCESS  read-only
              STATUS  mandatory
              DESCRIPTION
                      "The unit of the sensor."
              ::= { s47 3 }

	    s47valueInt OBJECT-TYPE
              SYNTAX  INTEGER
              ACCESS  read-write
              STATUS  mandatory
              DESCRIPTION
                      "The value of the sensor times 1000 as integer"
              ::= { s47 4 }

	    s47name OBJECT-TYPE
              SYNTAX  DisplayString
              ACCESS  read-only
              STATUS  mandatory
              DESCRIPTION
                      "The name of the sensor as String. 
		       This name is set by the user in the SNMP Config Table."
              ::= { s47 5 }

	    s47alarmInt OBJECT-TYPE
              SYNTAX  INTEGER
              ACCESS  read-only
              STATUS  mandatory
              DESCRIPTION
                      "The Sensor Alarm Status range 1..5 as integer"
              ::= { s47 6 }

	    s47LoLimitAlarmInt OBJECT-TYPE
              SYNTAX  INTEGER
              ACCESS  read-only
              STATUS  mandatory
              DESCRIPTION
                      "The lower limit alarm value of the sensor times 1000 as integer"
              ::= { s47 7 }

	    s47LoLimitWarnInt OBJECT-TYPE
              SYNTAX  INTEGER
              ACCESS  read-only
              STATUS  mandatory
              DESCRIPTION
                      "The lower limit warning value of the sensor times 1000 as integer"
              ::= { s47 8 }

	    s47HiLimitWarnInt OBJECT-TYPE
              SYNTAX  INTEGER
              ACCESS  read-only
              STATUS  mandatory
              DESCRIPTION
                      "The upper limit warning value of the sensor times 1000 as integer"
              ::= { s47 9 }

	    s47HiLimitAlarmInt OBJECT-TYPE
              SYNTAX  INTEGER
              ACCESS  read-only
              STATUS  mandatory
              DESCRIPTION
                      "The upper limit alarm value of the sensor times 1000 as integer"
              ::= { s47 10 }

	    s47HysterInt OBJECT-TYPE
              SYNTAX  INTEGER
              ACCESS  read-only
              STATUS  mandatory
              DESCRIPTION
                      "The hysteresis value of the sensor times 1000 as integer"
              ::= { s47 11 }


	-- sensor48:
            s48id OBJECT-TYPE
              SYNTAX  DisplayString
              ACCESS  read-only
              STATUS  mandatory
              DESCRIPTION
                      "A unique value containing sensortype and serial number."
              ::= { s48 1 }

	    s48value OBJECT-TYPE
              SYNTAX  DisplayString
              ACCESS  read-only
              STATUS  mandatory
              DESCRIPTION
                      "The value of the sensor as String."
              ::= { s48 2 }

	    s48unit OBJECT-TYPE
              SYNTAX  DisplayString
              ACCESS  read-only
              STATUS  mandatory
              DESCRIPTION
                      "The unit of the sensor."
              ::= { s48 3 }

	    s48valueInt OBJECT-TYPE
              SYNTAX  INTEGER
              ACCESS  read-write
              STATUS  mandatory
              DESCRIPTION
                      "The value of the sensor times 1000 as integer"
              ::= { s48 4 }

	    s48name OBJECT-TYPE
              SYNTAX  DisplayString
              ACCESS  read-only
              STATUS  mandatory
              DESCRIPTION
                      "The name of the sensor as String. 
		       This name is set by the user in the SNMP Config Table."
              ::= { s48 5 }

	    s48alarmInt OBJECT-TYPE
              SYNTAX  INTEGER
              ACCESS  read-only
              STATUS  mandatory
              DESCRIPTION
                      "The Sensor Alarm Status range 1..5 as integer"
              ::= { s48 6 }

	    s48LoLimitAlarmInt OBJECT-TYPE
              SYNTAX  INTEGER
              ACCESS  read-only
              STATUS  mandatory
              DESCRIPTION
                      "The lower limit alarm value of the sensor times 1000 as integer"
              ::= { s48 7 }

	    s48LoLimitWarnInt OBJECT-TYPE
              SYNTAX  INTEGER
              ACCESS  read-only
              STATUS  mandatory
              DESCRIPTION
                      "The lower limit warning value of the sensor times 1000 as integer"
              ::= { s48 8 }

	    s48HiLimitWarnInt OBJECT-TYPE
              SYNTAX  INTEGER
              ACCESS  read-only
              STATUS  mandatory
              DESCRIPTION
                      "The upper limit warning value of the sensor times 1000 as integer"
              ::= { s48 9 }

	    s48HiLimitAlarmInt OBJECT-TYPE
              SYNTAX  INTEGER
              ACCESS  read-only
              STATUS  mandatory
              DESCRIPTION
                      "The upper limit alarm value of the sensor times 1000 as integer"
              ::= { s48 10 }

	    s48HysterInt OBJECT-TYPE
              SYNTAX  INTEGER
              ACCESS  read-only
              STATUS  mandatory
              DESCRIPTION
                      "The hysteresis value of the sensor times 1000 as integer"
              ::= { s48 11 }


	-- sensor49:
            s49id OBJECT-TYPE
              SYNTAX  DisplayString
              ACCESS  read-only
              STATUS  mandatory
              DESCRIPTION
                      "A unique value containing sensortype and serial number."
              ::= { s49 1 }

	    s49value OBJECT-TYPE
              SYNTAX  DisplayString
              ACCESS  read-only
              STATUS  mandatory
              DESCRIPTION
                      "The value of the sensor as String."
              ::= { s49 2 }

	    s49unit OBJECT-TYPE
              SYNTAX  DisplayString
              ACCESS  read-only
              STATUS  mandatory
              DESCRIPTION
                      "The unit of the sensor."
              ::= { s49 3 }

	    s49valueInt OBJECT-TYPE
              SYNTAX  INTEGER
              ACCESS  read-write
              STATUS  mandatory
              DESCRIPTION
                      "The value of the sensor times 1000 as integer"
              ::= { s49 4 }

	    s49name OBJECT-TYPE
              SYNTAX  DisplayString
              ACCESS  read-only
              STATUS  mandatory
              DESCRIPTION
                      "The name of the sensor as String. 
		       This name is set by the user in the SNMP Config Table."
              ::= { s49 5 }

	    s49alarmInt OBJECT-TYPE
              SYNTAX  INTEGER
              ACCESS  read-only
              STATUS  mandatory
              DESCRIPTION
                      "The Sensor Alarm Status range 1..5 as integer"
              ::= { s49 6 }

	    s49LoLimitAlarmInt OBJECT-TYPE
              SYNTAX  INTEGER
              ACCESS  read-only
              STATUS  mandatory
              DESCRIPTION
                      "The lower limit alarm value of the sensor times 1000 as integer"
              ::= { s49 7 }

	    s49LoLimitWarnInt OBJECT-TYPE
              SYNTAX  INTEGER
              ACCESS  read-only
              STATUS  mandatory
              DESCRIPTION
                      "The lower limit warning value of the sensor times 1000 as integer"
              ::= { s49 8 }

	    s49HiLimitWarnInt OBJECT-TYPE
              SYNTAX  INTEGER
              ACCESS  read-only
              STATUS  mandatory
              DESCRIPTION
                      "The upper limit warning value of the sensor times 1000 as integer"
              ::= { s49 9 }

	    s49HiLimitAlarmInt OBJECT-TYPE
              SYNTAX  INTEGER
              ACCESS  read-only
              STATUS  mandatory
              DESCRIPTION
                      "The upper limit alarm value of the sensor times 1000 as integer"
              ::= { s49 10 }

	    s49HysterInt OBJECT-TYPE
              SYNTAX  INTEGER
              ACCESS  read-only
              STATUS  mandatory
              DESCRIPTION
                      "The hysteresis value of the sensor times 1000 as integer"
              ::= { s49 11 }


	-- sensor50:
            s50id OBJECT-TYPE
              SYNTAX  DisplayString
              ACCESS  read-only
              STATUS  mandatory
              DESCRIPTION
                      "A unique value containing sensortype and serial number."
              ::= { s50 1 }

	    s50value OBJECT-TYPE
              SYNTAX  DisplayString
              ACCESS  read-only
              STATUS  mandatory
              DESCRIPTION
                      "The value of the sensor as String."
              ::= { s50 2 }

	    s50unit OBJECT-TYPE
              SYNTAX  DisplayString
              ACCESS  read-only
              STATUS  mandatory
              DESCRIPTION
                      "The unit of the sensor."
              ::= { s50 3 }

	    s50valueInt OBJECT-TYPE
              SYNTAX  INTEGER
              ACCESS  read-write
              STATUS  mandatory
              DESCRIPTION
                      "The value of the sensor times 1000 as integer"
              ::= { s50 4 }

	    s50name OBJECT-TYPE
              SYNTAX  DisplayString
              ACCESS  read-only
              STATUS  mandatory
              DESCRIPTION
                      "The name of the sensor as String. 
		       This name is set by the user in the SNMP Config Table."
              ::= { s50 5 }

	    s50alarmInt OBJECT-TYPE
              SYNTAX  INTEGER
              ACCESS  read-only
              STATUS  mandatory
              DESCRIPTION
                      "The Sensor Alarm Status range 1..5 as integer"
              ::= { s50 6 }

	    s50LoLimitAlarmInt OBJECT-TYPE
              SYNTAX  INTEGER
              ACCESS  read-only
              STATUS  mandatory
              DESCRIPTION
                      "The lower limit alarm value of the sensor times 1000 as integer"
              ::= { s50 7 }

	    s50LoLimitWarnInt OBJECT-TYPE
              SYNTAX  INTEGER
              ACCESS  read-only
              STATUS  mandatory
              DESCRIPTION
                      "The lower limit warning value of the sensor times 1000 as integer"
              ::= { s50 8 }

	    s50HiLimitWarnInt OBJECT-TYPE
              SYNTAX  INTEGER
              ACCESS  read-only
              STATUS  mandatory
              DESCRIPTION
                      "The upper limit warning value of the sensor times 1000 as integer"
              ::= { s50 9 }

	    s50HiLimitAlarmInt OBJECT-TYPE
              SYNTAX  INTEGER
              ACCESS  read-only
              STATUS  mandatory
              DESCRIPTION
                      "The upper limit alarm value of the sensor times 1000 as integer"
              ::= { s50 10 }

	    s50HysterInt OBJECT-TYPE
              SYNTAX  INTEGER
              ACCESS  read-only
              STATUS  mandatory
              DESCRIPTION
                      "The hysteresis value of the sensor times 1000 as integer"
              ::= { s50 11 }


  --  51 - 60
	-- sensor51:
            s51id OBJECT-TYPE
              SYNTAX  DisplayString
              ACCESS  read-only
              STATUS  mandatory
              DESCRIPTION
                      "A unique value containing sensortype and serial number."
              ::= { s51 1 }

	    s51value OBJECT-TYPE
              SYNTAX  DisplayString
              ACCESS  read-only
              STATUS  mandatory
              DESCRIPTION
                      "The value of the sensor as String."
              ::= { s51 2 }

	    s51unit OBJECT-TYPE
              SYNTAX  DisplayString
              ACCESS  read-only
              STATUS  mandatory
              DESCRIPTION
                      "The unit of the sensor."
              ::= { s51 3 }

	    s51valueInt OBJECT-TYPE
              SYNTAX  INTEGER
              ACCESS  read-write
              STATUS  mandatory
              DESCRIPTION
                      "The value of the sensor times 1000 as integer"
              ::= { s51 4 }

	    s51name OBJECT-TYPE
              SYNTAX  DisplayString
              ACCESS  read-only
              STATUS  mandatory
              DESCRIPTION
                      "The name of the sensor as String. 
		       This name is set by the user in the SNMP Config Table."
              ::= { s51 5 }

	    s51alarmInt OBJECT-TYPE
              SYNTAX  INTEGER
              ACCESS  read-only
              STATUS  mandatory
              DESCRIPTION
                      "The Sensor Alarm Status range 1..5 as integer"
              ::= { s51 6 }

	    s51LoLimitAlarmInt OBJECT-TYPE
              SYNTAX  INTEGER
              ACCESS  read-only
              STATUS  mandatory
              DESCRIPTION
                      "The lower limit alarm value of the sensor times 1000 as integer"
              ::= { s51 7 }

	    s51LoLimitWarnInt OBJECT-TYPE
              SYNTAX  INTEGER
              ACCESS  read-only
              STATUS  mandatory
              DESCRIPTION
                      "The lower limit warning value of the sensor times 1000 as integer"
              ::= { s51 8 }

	    s51HiLimitWarnInt OBJECT-TYPE
              SYNTAX  INTEGER
              ACCESS  read-only
              STATUS  mandatory
              DESCRIPTION
                      "The upper limit warning value of the sensor times 1000 as integer"
              ::= { s51 9 }

	    s51HiLimitAlarmInt OBJECT-TYPE
              SYNTAX  INTEGER
              ACCESS  read-only
              STATUS  mandatory
              DESCRIPTION
                      "The upper limit alarm value of the sensor times 1000 as integer"
              ::= { s51 10 }

	    s51HysterInt OBJECT-TYPE
              SYNTAX  INTEGER
              ACCESS  read-only
              STATUS  mandatory
              DESCRIPTION
                      "The hysteresis value of the sensor times 1000 as integer"
              ::= { s51 11 }


	-- sensor52:
            s52id OBJECT-TYPE
              SYNTAX  DisplayString
              ACCESS  read-only
              STATUS  mandatory
              DESCRIPTION
                      "A unique value containing sensortype and serial number."
              ::= { s52 1 }

	    s52value OBJECT-TYPE
              SYNTAX  DisplayString
              ACCESS  read-only
              STATUS  mandatory
              DESCRIPTION
                      "The value of the sensor as String."
              ::= { s52 2 }

	    s52unit OBJECT-TYPE
              SYNTAX  DisplayString
              ACCESS  read-only
              STATUS  mandatory
              DESCRIPTION
                      "The unit of the sensor."
              ::= { s52 3 }

	    s52valueInt OBJECT-TYPE
              SYNTAX  INTEGER
              ACCESS  read-write
              STATUS  mandatory
              DESCRIPTION
                      "The value of the sensor times 1000 as integer"
              ::= { s52 4 }

	    s52name OBJECT-TYPE
              SYNTAX  DisplayString
              ACCESS  read-only
              STATUS  mandatory
              DESCRIPTION
                      "The name of the sensor as String. 
		       This name is set by the user in the SNMP Config Table."
              ::= { s52 5 }

	    s52alarmInt OBJECT-TYPE
              SYNTAX  INTEGER
              ACCESS  read-only
              STATUS  mandatory
              DESCRIPTION
                      "The Sensor Alarm Status range 1..5 as integer"
              ::= { s52 6 }

	    s52LoLimitAlarmInt OBJECT-TYPE
              SYNTAX  INTEGER
              ACCESS  read-only
              STATUS  mandatory
              DESCRIPTION
                      "The lower limit alarm value of the sensor times 1000 as integer"
              ::= { s52 7 }

	    s52LoLimitWarnInt OBJECT-TYPE
              SYNTAX  INTEGER
              ACCESS  read-only
              STATUS  mandatory
              DESCRIPTION
                      "The lower limit warning value of the sensor times 1000 as integer"
              ::= { s52 8 }

	    s52HiLimitWarnInt OBJECT-TYPE
              SYNTAX  INTEGER
              ACCESS  read-only
              STATUS  mandatory
              DESCRIPTION
                      "The upper limit warning value of the sensor times 1000 as integer"
              ::= { s52 9 }

	    s52HiLimitAlarmInt OBJECT-TYPE
              SYNTAX  INTEGER
              ACCESS  read-only
              STATUS  mandatory
              DESCRIPTION
                      "The upper limit alarm value of the sensor times 1000 as integer"
              ::= { s52 10 }

	    s52HysterInt OBJECT-TYPE
              SYNTAX  INTEGER
              ACCESS  read-only
              STATUS  mandatory
              DESCRIPTION
                      "The hysteresis value of the sensor times 1000 as integer"
              ::= { s52 11 }


	-- sensor53:
            s53id OBJECT-TYPE
              SYNTAX  DisplayString
              ACCESS  read-only
              STATUS  mandatory
              DESCRIPTION
                      "A unique value containing sensortype and serial number."
              ::= { s53 1 }

	    s53value OBJECT-TYPE
              SYNTAX  DisplayString
              ACCESS  read-only
              STATUS  mandatory
              DESCRIPTION
                      "The value of the sensor as String."
              ::= { s53 2 }

	    s53unit OBJECT-TYPE
              SYNTAX  DisplayString
              ACCESS  read-only
              STATUS  mandatory
              DESCRIPTION
                      "The unit of the sensor."
              ::= { s53 3 }

	    s53valueInt OBJECT-TYPE
              SYNTAX  INTEGER
              ACCESS  read-write
              STATUS  mandatory
              DESCRIPTION
                      "The value of the sensor times 1000 as integer"
              ::= { s53 4 }

	    s53name OBJECT-TYPE
              SYNTAX  DisplayString
              ACCESS  read-only
              STATUS  mandatory
              DESCRIPTION
                      "The name of the sensor as String. 
		       This name is set by the user in the SNMP Config Table."
              ::= { s53 5 }

	    s53alarmInt OBJECT-TYPE
              SYNTAX  INTEGER
              ACCESS  read-only
              STATUS  mandatory
              DESCRIPTION
                      "The Sensor Alarm Status range 1..5 as integer"
              ::= { s53 6 }

	    s53LoLimitAlarmInt OBJECT-TYPE
              SYNTAX  INTEGER
              ACCESS  read-only
              STATUS  mandatory
              DESCRIPTION
                      "The lower limit alarm value of the sensor times 1000 as integer"
              ::= { s53 7 }

	    s53LoLimitWarnInt OBJECT-TYPE
              SYNTAX  INTEGER
              ACCESS  read-only
              STATUS  mandatory
              DESCRIPTION
                      "The lower limit warning value of the sensor times 1000 as integer"
              ::= { s53 8 }

	    s53HiLimitWarnInt OBJECT-TYPE
              SYNTAX  INTEGER
              ACCESS  read-only
              STATUS  mandatory
              DESCRIPTION
                      "The upper limit warning value of the sensor times 1000 as integer"
              ::= { s53 9 }

	    s53HiLimitAlarmInt OBJECT-TYPE
              SYNTAX  INTEGER
              ACCESS  read-only
              STATUS  mandatory
              DESCRIPTION
                      "The upper limit alarm value of the sensor times 1000 as integer"
              ::= { s53 10 }

	    s53HysterInt OBJECT-TYPE
              SYNTAX  INTEGER
              ACCESS  read-only
              STATUS  mandatory
              DESCRIPTION
                      "The hysteresis value of the sensor times 1000 as integer"
              ::= { s53 11 }


	-- sensor54:
            s54id OBJECT-TYPE
              SYNTAX  DisplayString
              ACCESS  read-only
              STATUS  mandatory
              DESCRIPTION
                      "A unique value containing sensortype and serial number."
              ::= { s54 1 }

	    s54value OBJECT-TYPE
              SYNTAX  DisplayString
              ACCESS  read-only
              STATUS  mandatory
              DESCRIPTION
                      "The value of the sensor as String."
              ::= { s54 2 }

	    s54unit OBJECT-TYPE
              SYNTAX  DisplayString
              ACCESS  read-only
              STATUS  mandatory
              DESCRIPTION
                      "The unit of the sensor."
              ::= { s54 3 }

	    s54valueInt OBJECT-TYPE
              SYNTAX  INTEGER
              ACCESS  read-write
              STATUS  mandatory
              DESCRIPTION
                      "The value of the sensor times 1000 as integer"
              ::= { s54 4 }

	    s54name OBJECT-TYPE
              SYNTAX  DisplayString
              ACCESS  read-only
              STATUS  mandatory
              DESCRIPTION
                      "The name of the sensor as String. 
		       This name is set by the user in the SNMP Config Table."
              ::= { s54 5 }

	    s54alarmInt OBJECT-TYPE
              SYNTAX  INTEGER
              ACCESS  read-only
              STATUS  mandatory
              DESCRIPTION
                      "The Sensor Alarm Status range 1..5 as integer"
              ::= { s54 6 }

	    s54LoLimitAlarmInt OBJECT-TYPE
              SYNTAX  INTEGER
              ACCESS  read-only
              STATUS  mandatory
              DESCRIPTION
                      "The lower limit alarm value of the sensor times 1000 as integer"
              ::= { s54 7 }

	    s54LoLimitWarnInt OBJECT-TYPE
              SYNTAX  INTEGER
              ACCESS  read-only
              STATUS  mandatory
              DESCRIPTION
                      "The lower limit warning value of the sensor times 1000 as integer"
              ::= { s54 8 }

	    s54HiLimitWarnInt OBJECT-TYPE
              SYNTAX  INTEGER
              ACCESS  read-only
              STATUS  mandatory
              DESCRIPTION
                      "The upper limit warning value of the sensor times 1000 as integer"
              ::= { s54 9 }

	    s54HiLimitAlarmInt OBJECT-TYPE
              SYNTAX  INTEGER
              ACCESS  read-only
              STATUS  mandatory
              DESCRIPTION
                      "The upper limit alarm value of the sensor times 1000 as integer"
              ::= { s54 10 }

	    s54HysterInt OBJECT-TYPE
              SYNTAX  INTEGER
              ACCESS  read-only
              STATUS  mandatory
              DESCRIPTION
                      "The hysteresis value of the sensor times 1000 as integer"
              ::= { s54 11 }


	-- sensor55:
            s55id OBJECT-TYPE
              SYNTAX  DisplayString
              ACCESS  read-only
              STATUS  mandatory
              DESCRIPTION
                      "A unique value containing sensortype and serial number."
              ::= { s55 1 }

	    s55value OBJECT-TYPE
              SYNTAX  DisplayString
              ACCESS  read-only
              STATUS  mandatory
              DESCRIPTION
                      "The value of the sensor as String."
              ::= { s55 2 }

	    s55unit OBJECT-TYPE
              SYNTAX  DisplayString
              ACCESS  read-only
              STATUS  mandatory
              DESCRIPTION
                      "The unit of the sensor."
              ::= { s55 3 }

	    s55valueInt OBJECT-TYPE
              SYNTAX  INTEGER
              ACCESS  read-write
              STATUS  mandatory
              DESCRIPTION
                      "The value of the sensor times 1000 as integer"
              ::= { s55 4 }

	    s55name OBJECT-TYPE
              SYNTAX  DisplayString
              ACCESS  read-only
              STATUS  mandatory
              DESCRIPTION
                      "The name of the sensor as String. 
		       This name is set by the user in the SNMP Config Table."
              ::= { s55 5 }

	    s55alarmInt OBJECT-TYPE
              SYNTAX  INTEGER
              ACCESS  read-only
              STATUS  mandatory
              DESCRIPTION
                      "The Sensor Alarm Status range 1..5 as integer"
              ::= { s55 6 }

	    s55LoLimitAlarmInt OBJECT-TYPE
              SYNTAX  INTEGER
              ACCESS  read-only
              STATUS  mandatory
              DESCRIPTION
                      "The lower limit alarm value of the sensor times 1000 as integer"
              ::= { s55 7 }

	    s55LoLimitWarnInt OBJECT-TYPE
              SYNTAX  INTEGER
              ACCESS  read-only
              STATUS  mandatory
              DESCRIPTION
                      "The lower limit warning value of the sensor times 1000 as integer"
              ::= { s55 8 }

	    s55HiLimitWarnInt OBJECT-TYPE
              SYNTAX  INTEGER
              ACCESS  read-only
              STATUS  mandatory
              DESCRIPTION
                      "The upper limit warning value of the sensor times 1000 as integer"
              ::= { s55 9 }

	    s55HiLimitAlarmInt OBJECT-TYPE
              SYNTAX  INTEGER
              ACCESS  read-only
              STATUS  mandatory
              DESCRIPTION
                      "The upper limit alarm value of the sensor times 1000 as integer"
              ::= { s55 10 }

	    s55HysterInt OBJECT-TYPE
              SYNTAX  INTEGER
              ACCESS  read-only
              STATUS  mandatory
              DESCRIPTION
                      "The hysteresis value of the sensor times 1000 as integer"
              ::= { s55 11 }


	-- sensor56:
            s56id OBJECT-TYPE
              SYNTAX  DisplayString
              ACCESS  read-only
              STATUS  mandatory
              DESCRIPTION
                      "A unique value containing sensortype and serial number."
              ::= { s56 1 }

	    s56value OBJECT-TYPE
              SYNTAX  DisplayString
              ACCESS  read-only
              STATUS  mandatory
              DESCRIPTION
                      "The value of the sensor as String."
              ::= { s56 2 }

	    s56unit OBJECT-TYPE
              SYNTAX  DisplayString
              ACCESS  read-only
              STATUS  mandatory
              DESCRIPTION
                      "The unit of the sensor."
              ::= { s56 3 }

	    s56valueInt OBJECT-TYPE
              SYNTAX  INTEGER
              ACCESS  read-write
              STATUS  mandatory
              DESCRIPTION
                      "The value of the sensor times 1000 as integer"
              ::= { s56 4 }

	    s56name OBJECT-TYPE
              SYNTAX  DisplayString
              ACCESS  read-only
              STATUS  mandatory
              DESCRIPTION
                      "The name of the sensor as String. 
		       This name is set by the user in the SNMP Config Table."
              ::= { s56 5 }

	    s56alarmInt OBJECT-TYPE
              SYNTAX  INTEGER
              ACCESS  read-only
              STATUS  mandatory
              DESCRIPTION
                      "The Sensor Alarm Status range 1..5 as integer"
              ::= { s56 6 }

	    s56LoLimitAlarmInt OBJECT-TYPE
              SYNTAX  INTEGER
              ACCESS  read-only
              STATUS  mandatory
              DESCRIPTION
                      "The lower limit alarm value of the sensor times 1000 as integer"
              ::= { s56 7 }

	    s56LoLimitWarnInt OBJECT-TYPE
              SYNTAX  INTEGER
              ACCESS  read-only
              STATUS  mandatory
              DESCRIPTION
                      "The lower limit warning value of the sensor times 1000 as integer"
              ::= { s56 8 }

	    s56HiLimitWarnInt OBJECT-TYPE
              SYNTAX  INTEGER
              ACCESS  read-only
              STATUS  mandatory
              DESCRIPTION
                      "The upper limit warning value of the sensor times 1000 as integer"
              ::= { s56 9 }

	    s56HiLimitAlarmInt OBJECT-TYPE
              SYNTAX  INTEGER
              ACCESS  read-only
              STATUS  mandatory
              DESCRIPTION
                      "The upper limit alarm value of the sensor times 1000 as integer"
              ::= { s56 10 }

	    s56HysterInt OBJECT-TYPE
              SYNTAX  INTEGER
              ACCESS  read-only
              STATUS  mandatory
              DESCRIPTION
                      "The hysteresis value of the sensor times 1000 as integer"
              ::= { s56 11 }


	-- sensor57:
            s57id OBJECT-TYPE
              SYNTAX  DisplayString
              ACCESS  read-only
              STATUS  mandatory
              DESCRIPTION
                      "A unique value containing sensortype and serial number."
              ::= { s57 1 }

	    s57value OBJECT-TYPE
              SYNTAX  DisplayString
              ACCESS  read-only
              STATUS  mandatory
              DESCRIPTION
                      "The value of the sensor as String."
              ::= { s57 2 }

	    s57unit OBJECT-TYPE
              SYNTAX  DisplayString
              ACCESS  read-only
              STATUS  mandatory
              DESCRIPTION
                      "The unit of the sensor."
              ::= { s57 3 }

	    s57valueInt OBJECT-TYPE
              SYNTAX  INTEGER
              ACCESS  read-write
              STATUS  mandatory
              DESCRIPTION
                      "The value of the sensor times 1000 as integer"
              ::= { s57 4 }

	    s57name OBJECT-TYPE
              SYNTAX  DisplayString
              ACCESS  read-only
              STATUS  mandatory
              DESCRIPTION
                      "The name of the sensor as String. 
		       This name is set by the user in the SNMP Config Table."
              ::= { s57 5 }

	    s57alarmInt OBJECT-TYPE
              SYNTAX  INTEGER
              ACCESS  read-only
              STATUS  mandatory
              DESCRIPTION
                      "The Sensor Alarm Status range 1..5 as integer"
              ::= { s57 6 }

	    s57LoLimitAlarmInt OBJECT-TYPE
              SYNTAX  INTEGER
              ACCESS  read-only
              STATUS  mandatory
              DESCRIPTION
                      "The lower limit alarm value of the sensor times 1000 as integer"
              ::= { s57 7 }

	    s57LoLimitWarnInt OBJECT-TYPE
              SYNTAX  INTEGER
              ACCESS  read-only
              STATUS  mandatory
              DESCRIPTION
                      "The lower limit warning value of the sensor times 1000 as integer"
              ::= { s57 8 }

	    s57HiLimitWarnInt OBJECT-TYPE
              SYNTAX  INTEGER
              ACCESS  read-only
              STATUS  mandatory
              DESCRIPTION
                      "The upper limit warning value of the sensor times 1000 as integer"
              ::= { s57 9 }

	    s57HiLimitAlarmInt OBJECT-TYPE
              SYNTAX  INTEGER
              ACCESS  read-only
              STATUS  mandatory
              DESCRIPTION
                      "The upper limit alarm value of the sensor times 1000 as integer"
              ::= { s57 10 }

	    s57HysterInt OBJECT-TYPE
              SYNTAX  INTEGER
              ACCESS  read-only
              STATUS  mandatory
              DESCRIPTION
                      "The hysteresis value of the sensor times 1000 as integer"
              ::= { s57 11 }


	-- sensor58:
            s58id OBJECT-TYPE
              SYNTAX  DisplayString
              ACCESS  read-only
              STATUS  mandatory
              DESCRIPTION
                      "A unique value containing sensortype and serial number."
              ::= { s58 1 }

	    s58value OBJECT-TYPE
              SYNTAX  DisplayString
              ACCESS  read-only
              STATUS  mandatory
              DESCRIPTION
                      "The value of the sensor as String."
              ::= { s58 2 }

	    s58unit OBJECT-TYPE
              SYNTAX  DisplayString
              ACCESS  read-only
              STATUS  mandatory
              DESCRIPTION
                      "The unit of the sensor."
              ::= { s58 3 }

	    s58valueInt OBJECT-TYPE
              SYNTAX  INTEGER
              ACCESS  read-write
              STATUS  mandatory
              DESCRIPTION
                      "The value of the sensor times 1000 as integer"
              ::= { s58 4 }

	    s58name OBJECT-TYPE
              SYNTAX  DisplayString
              ACCESS  read-only
              STATUS  mandatory
              DESCRIPTION
                      "The name of the sensor as String. 
		       This name is set by the user in the SNMP Config Table."
              ::= { s58 5 }

	    s58alarmInt OBJECT-TYPE
              SYNTAX  INTEGER
              ACCESS  read-only
              STATUS  mandatory
              DESCRIPTION
                      "The Sensor Alarm Status range 1..5 as integer"
              ::= { s58 6 }

	    s58LoLimitAlarmInt OBJECT-TYPE
              SYNTAX  INTEGER
              ACCESS  read-only
              STATUS  mandatory
              DESCRIPTION
                      "The lower limit alarm value of the sensor times 1000 as integer"
              ::= { s58 7 }

	    s58LoLimitWarnInt OBJECT-TYPE
              SYNTAX  INTEGER
              ACCESS  read-only
              STATUS  mandatory
              DESCRIPTION
                      "The lower limit warning value of the sensor times 1000 as integer"
              ::= { s58 8 }

	    s58HiLimitWarnInt OBJECT-TYPE
              SYNTAX  INTEGER
              ACCESS  read-only
              STATUS  mandatory
              DESCRIPTION
                      "The upper limit warning value of the sensor times 1000 as integer"
              ::= { s58 9 }

	    s58HiLimitAlarmInt OBJECT-TYPE
              SYNTAX  INTEGER
              ACCESS  read-only
              STATUS  mandatory
              DESCRIPTION
                      "The upper limit alarm value of the sensor times 1000 as integer"
              ::= { s58 10 }

	    s58HysterInt OBJECT-TYPE
              SYNTAX  INTEGER
              ACCESS  read-only
              STATUS  mandatory
              DESCRIPTION
                      "The hysteresis value of the sensor times 1000 as integer"
              ::= { s58 11 }


	-- sensor59:
            s59id OBJECT-TYPE
              SYNTAX  DisplayString
              ACCESS  read-only
              STATUS  mandatory
              DESCRIPTION
                      "A unique value containing sensortype and serial number."
              ::= { s59 1 }

	    s59value OBJECT-TYPE
              SYNTAX  DisplayString
              ACCESS  read-only
              STATUS  mandatory
              DESCRIPTION
                      "The value of the sensor as String."
              ::= { s59 2 }

	    s59unit OBJECT-TYPE
              SYNTAX  DisplayString
              ACCESS  read-only
              STATUS  mandatory
              DESCRIPTION
                      "The unit of the sensor."
              ::= { s59 3 }

	    s59valueInt OBJECT-TYPE
              SYNTAX  INTEGER
              ACCESS  read-write
              STATUS  mandatory
              DESCRIPTION
                      "The value of the sensor times 1000 as integer"
              ::= { s59 4 }

	    s59name OBJECT-TYPE
              SYNTAX  DisplayString
              ACCESS  read-only
              STATUS  mandatory
              DESCRIPTION
                      "The name of the sensor as String. 
		       This name is set by the user in the SNMP Config Table."
              ::= { s59 5 }

	    s59alarmInt OBJECT-TYPE
              SYNTAX  INTEGER
              ACCESS  read-only
              STATUS  mandatory
              DESCRIPTION
                      "The Sensor Alarm Status range 1..5 as integer"
              ::= { s59 6 }

	    s59LoLimitAlarmInt OBJECT-TYPE
              SYNTAX  INTEGER
              ACCESS  read-only
              STATUS  mandatory
              DESCRIPTION
                      "The lower limit alarm value of the sensor times 1000 as integer"
              ::= { s59 7 }

	    s59LoLimitWarnInt OBJECT-TYPE
              SYNTAX  INTEGER
              ACCESS  read-only
              STATUS  mandatory
              DESCRIPTION
                      "The lower limit warning value of the sensor times 1000 as integer"
              ::= { s59 8 }

	    s59HiLimitWarnInt OBJECT-TYPE
              SYNTAX  INTEGER
              ACCESS  read-only
              STATUS  mandatory
              DESCRIPTION
                      "The upper limit warning value of the sensor times 1000 as integer"
              ::= { s59 9 }

	    s59HiLimitAlarmInt OBJECT-TYPE
              SYNTAX  INTEGER
              ACCESS  read-only
              STATUS  mandatory
              DESCRIPTION
                      "The upper limit alarm value of the sensor times 1000 as integer"
              ::= { s59 10 }

	    s59HysterInt OBJECT-TYPE
              SYNTAX  INTEGER
              ACCESS  read-only
              STATUS  mandatory
              DESCRIPTION
                      "The hysteresis value of the sensor times 1000 as integer"
              ::= { s59 11 }


	-- sensor60:
            s60id OBJECT-TYPE
              SYNTAX  DisplayString
              ACCESS  read-only
              STATUS  mandatory
              DESCRIPTION
                      "A unique value containing sensortype and serial number."
              ::= { s60 1 }

	    s60value OBJECT-TYPE
              SYNTAX  DisplayString
              ACCESS  read-only
              STATUS  mandatory
              DESCRIPTION
                      "The value of the sensor as String."
              ::= { s60 2 }

	    s60unit OBJECT-TYPE
              SYNTAX  DisplayString
              ACCESS  read-only
              STATUS  mandatory
              DESCRIPTION
                      "The unit of the sensor."
              ::= { s60 3 }

	    s60valueInt OBJECT-TYPE
              SYNTAX  INTEGER
              ACCESS  read-write
              STATUS  mandatory
              DESCRIPTION
                      "The value of the sensor times 1000 as integer"
              ::= { s60 4 }

	    s60name OBJECT-TYPE
              SYNTAX  DisplayString
              ACCESS  read-only
              STATUS  mandatory
              DESCRIPTION
                      "The name of the sensor as String. 
		       This name is set by the user in the SNMP Config Table."
              ::= { s60 5 }

	    s60alarmInt OBJECT-TYPE
              SYNTAX  INTEGER
              ACCESS  read-only
              STATUS  mandatory
              DESCRIPTION
                      "The Sensor Alarm Status range 1..5 as integer"
              ::= { s60 6 }

	    s60LoLimitAlarmInt OBJECT-TYPE
              SYNTAX  INTEGER
              ACCESS  read-only
              STATUS  mandatory
              DESCRIPTION
                      "The lower limit alarm value of the sensor times 1000 as integer"
              ::= { s60 7 }

	    s60LoLimitWarnInt OBJECT-TYPE
              SYNTAX  INTEGER
              ACCESS  read-only
              STATUS  mandatory
              DESCRIPTION
                      "The lower limit warning value of the sensor times 1000 as integer"
              ::= { s60 8 }

	    s60HiLimitWarnInt OBJECT-TYPE
              SYNTAX  INTEGER
              ACCESS  read-only
              STATUS  mandatory
              DESCRIPTION
                      "The upper limit warning value of the sensor times 1000 as integer"
              ::= { s60 9 }

	    s60HiLimitAlarmInt OBJECT-TYPE
              SYNTAX  INTEGER
              ACCESS  read-only
              STATUS  mandatory
              DESCRIPTION
                      "The upper limit alarm value of the sensor times 1000 as integer"
              ::= { s60 10 }

	    s60HysterInt OBJECT-TYPE
              SYNTAX  INTEGER
              ACCESS  read-only
              STATUS  mandatory
              DESCRIPTION
                      "The hysteresis value of the sensor times 1000 as integer"
              ::= { s60 11 }


  --  61 - 70
	-- sensor61:
            s61id OBJECT-TYPE
              SYNTAX  DisplayString
              ACCESS  read-only
              STATUS  mandatory
              DESCRIPTION
                      "A unique value containing sensortype and serial number."
              ::= { s61 1 }

	    s61value OBJECT-TYPE
              SYNTAX  DisplayString
              ACCESS  read-only
              STATUS  mandatory
              DESCRIPTION
                      "The value of the sensor as String."
              ::= { s61 2 }

	    s61unit OBJECT-TYPE
              SYNTAX  DisplayString
              ACCESS  read-only
              STATUS  mandatory
              DESCRIPTION
                      "The unit of the sensor."
              ::= { s61 3 }

	    s61valueInt OBJECT-TYPE
              SYNTAX  INTEGER
              ACCESS  read-write
              STATUS  mandatory
              DESCRIPTION
                      "The value of the sensor times 1000 as integer"
              ::= { s61 4 }

	    s61name OBJECT-TYPE
              SYNTAX  DisplayString
              ACCESS  read-only
              STATUS  mandatory
              DESCRIPTION
                      "The name of the sensor as String. 
		       This name is set by the user in the SNMP Config Table."
              ::= { s61 5 }

	    s61alarmInt OBJECT-TYPE
              SYNTAX  INTEGER
              ACCESS  read-only
              STATUS  mandatory
              DESCRIPTION
                      "The Sensor Alarm Status range 1..5 as integer"
              ::= { s61 6 }

	    s61LoLimitAlarmInt OBJECT-TYPE
              SYNTAX  INTEGER
              ACCESS  read-only
              STATUS  mandatory
              DESCRIPTION
                      "The lower limit alarm value of the sensor times 1000 as integer"
              ::= { s61 7 }

	    s61LoLimitWarnInt OBJECT-TYPE
              SYNTAX  INTEGER
              ACCESS  read-only
              STATUS  mandatory
              DESCRIPTION
                      "The lower limit warning value of the sensor times 1000 as integer"
              ::= { s61 8 }

	    s61HiLimitWarnInt OBJECT-TYPE
              SYNTAX  INTEGER
              ACCESS  read-only
              STATUS  mandatory
              DESCRIPTION
                      "The upper limit warning value of the sensor times 1000 as integer"
              ::= { s61 9 }

	    s61HiLimitAlarmInt OBJECT-TYPE
              SYNTAX  INTEGER
              ACCESS  read-only
              STATUS  mandatory
              DESCRIPTION
                      "The upper limit alarm value of the sensor times 1000 as integer"
              ::= { s61 10 }

	    s61HysterInt OBJECT-TYPE
              SYNTAX  INTEGER
              ACCESS  read-only
              STATUS  mandatory
              DESCRIPTION
                      "The hysteresis value of the sensor times 1000 as integer"
              ::= { s61 11 }


	-- sensor62:
            s62id OBJECT-TYPE
              SYNTAX  DisplayString
              ACCESS  read-only
              STATUS  mandatory
              DESCRIPTION
                      "A unique value containing sensortype and serial number."
              ::= { s62 1 }

	    s62value OBJECT-TYPE
              SYNTAX  DisplayString
              ACCESS  read-only
              STATUS  mandatory
              DESCRIPTION
                      "The value of the sensor as String."
              ::= { s62 2 }

	    s62unit OBJECT-TYPE
              SYNTAX  DisplayString
              ACCESS  read-only
              STATUS  mandatory
              DESCRIPTION
                      "The unit of the sensor."
              ::= { s62 3 }

	    s62valueInt OBJECT-TYPE
              SYNTAX  INTEGER
              ACCESS  read-write
              STATUS  mandatory
              DESCRIPTION
                      "The value of the sensor times 1000 as integer"
              ::= { s62 4 }

	    s62name OBJECT-TYPE
              SYNTAX  DisplayString
              ACCESS  read-only
              STATUS  mandatory
              DESCRIPTION
                      "The name of the sensor as String. 
		       This name is set by the user in the SNMP Config Table."
              ::= { s62 5 }

	    s62alarmInt OBJECT-TYPE
              SYNTAX  INTEGER
              ACCESS  read-only
              STATUS  mandatory
              DESCRIPTION
                      "The Sensor Alarm Status range 1..5 as integer"
              ::= { s62 6 }

	    s62LoLimitAlarmInt OBJECT-TYPE
              SYNTAX  INTEGER
              ACCESS  read-only
              STATUS  mandatory
              DESCRIPTION
                      "The lower limit alarm value of the sensor times 1000 as integer"
              ::= { s62 7 }

	    s62LoLimitWarnInt OBJECT-TYPE
              SYNTAX  INTEGER
              ACCESS  read-only
              STATUS  mandatory
              DESCRIPTION
                      "The lower limit warning value of the sensor times 1000 as integer"
              ::= { s62 8 }

	    s62HiLimitWarnInt OBJECT-TYPE
              SYNTAX  INTEGER
              ACCESS  read-only
              STATUS  mandatory
              DESCRIPTION
                      "The upper limit warning value of the sensor times 1000 as integer"
              ::= { s62 9 }

	    s62HiLimitAlarmInt OBJECT-TYPE
              SYNTAX  INTEGER
              ACCESS  read-only
              STATUS  mandatory
              DESCRIPTION
                      "The upper limit alarm value of the sensor times 1000 as integer"
              ::= { s62 10 }

	    s62HysterInt OBJECT-TYPE
              SYNTAX  INTEGER
              ACCESS  read-only
              STATUS  mandatory
              DESCRIPTION
                      "The hysteresis value of the sensor times 1000 as integer"
              ::= { s62 11 }


	-- sensor63:
            s63id OBJECT-TYPE
              SYNTAX  DisplayString
              ACCESS  read-only
              STATUS  mandatory
              DESCRIPTION
                      "A unique value containing sensortype and serial number."
              ::= { s63 1 }

	    s63value OBJECT-TYPE
              SYNTAX  DisplayString
              ACCESS  read-only
              STATUS  mandatory
              DESCRIPTION
                      "The value of the sensor as String."
              ::= { s63 2 }

	    s63unit OBJECT-TYPE
              SYNTAX  DisplayString
              ACCESS  read-only
              STATUS  mandatory
              DESCRIPTION
                      "The unit of the sensor."
              ::= { s63 3 }

	    s63valueInt OBJECT-TYPE
              SYNTAX  INTEGER
              ACCESS  read-write
              STATUS  mandatory
              DESCRIPTION
                      "The value of the sensor times 1000 as integer"
              ::= { s63 4 }

	    s63name OBJECT-TYPE
              SYNTAX  DisplayString
              ACCESS  read-only
              STATUS  mandatory
              DESCRIPTION
                      "The name of the sensor as String. 
		       This name is set by the user in the SNMP Config Table."
              ::= { s63 5 }

	    s63alarmInt OBJECT-TYPE
              SYNTAX  INTEGER
              ACCESS  read-only
              STATUS  mandatory
              DESCRIPTION
                      "The Sensor Alarm Status range 1..5 as integer"
              ::= { s63 6 }

	    s63LoLimitAlarmInt OBJECT-TYPE
              SYNTAX  INTEGER
              ACCESS  read-only
              STATUS  mandatory
              DESCRIPTION
                      "The lower limit alarm value of the sensor times 1000 as integer"
              ::= { s63 7 }

	    s63LoLimitWarnInt OBJECT-TYPE
              SYNTAX  INTEGER
              ACCESS  read-only
              STATUS  mandatory
              DESCRIPTION
                      "The lower limit warning value of the sensor times 1000 as integer"
              ::= { s63 8 }

	    s63HiLimitWarnInt OBJECT-TYPE
              SYNTAX  INTEGER
              ACCESS  read-only
              STATUS  mandatory
              DESCRIPTION
                      "The upper limit warning value of the sensor times 1000 as integer"
              ::= { s63 9 }

	    s63HiLimitAlarmInt OBJECT-TYPE
              SYNTAX  INTEGER
              ACCESS  read-only
              STATUS  mandatory
              DESCRIPTION
                      "The upper limit alarm value of the sensor times 1000 as integer"
              ::= { s63 10 }

	    s63HysterInt OBJECT-TYPE
              SYNTAX  INTEGER
              ACCESS  read-only
              STATUS  mandatory
              DESCRIPTION
                      "The hysteresis value of the sensor times 1000 as integer"
              ::= { s63 11 }


	-- sensor64:
            s64id OBJECT-TYPE
              SYNTAX  DisplayString
              ACCESS  read-only
              STATUS  mandatory
              DESCRIPTION
                      "A unique value containing sensortype and serial number."
              ::= { s64 1 }

	    s64value OBJECT-TYPE
              SYNTAX  DisplayString
              ACCESS  read-only
              STATUS  mandatory
              DESCRIPTION
                      "The value of the sensor as String."
              ::= { s64 2 }

	    s64unit OBJECT-TYPE
              SYNTAX  DisplayString
              ACCESS  read-only
              STATUS  mandatory
              DESCRIPTION
                      "The unit of the sensor."
              ::= { s64 3 }

	    s64valueInt OBJECT-TYPE
              SYNTAX  INTEGER
              ACCESS  read-write
              STATUS  mandatory
              DESCRIPTION
                      "The value of the sensor times 1000 as integer"
              ::= { s64 4 }

	    s64name OBJECT-TYPE
              SYNTAX  DisplayString
              ACCESS  read-only
              STATUS  mandatory
              DESCRIPTION
                      "The name of the sensor as String. 
		       This name is set by the user in the SNMP Config Table."
              ::= { s64 5 }

	    s64alarmInt OBJECT-TYPE
              SYNTAX  INTEGER
              ACCESS  read-only
              STATUS  mandatory
              DESCRIPTION
                      "The Sensor Alarm Status range 1..5 as integer"
              ::= { s64 6 }

	    s64LoLimitAlarmInt OBJECT-TYPE
              SYNTAX  INTEGER
              ACCESS  read-only
              STATUS  mandatory
              DESCRIPTION
                      "The lower limit alarm value of the sensor times 1000 as integer"
              ::= { s64 7 }

	    s64LoLimitWarnInt OBJECT-TYPE
              SYNTAX  INTEGER
              ACCESS  read-only
              STATUS  mandatory
              DESCRIPTION
                      "The lower limit warning value of the sensor times 1000 as integer"
              ::= { s64 8 }

	    s64HiLimitWarnInt OBJECT-TYPE
              SYNTAX  INTEGER
              ACCESS  read-only
              STATUS  mandatory
              DESCRIPTION
                      "The upper limit warning value of the sensor times 1000 as integer"
              ::= { s64 9 }

	    s64HiLimitAlarmInt OBJECT-TYPE
              SYNTAX  INTEGER
              ACCESS  read-only
              STATUS  mandatory
              DESCRIPTION
                      "The upper limit alarm value of the sensor times 1000 as integer"
              ::= { s64 10 }

	    s64HysterInt OBJECT-TYPE
              SYNTAX  INTEGER
              ACCESS  read-only
              STATUS  mandatory
              DESCRIPTION
                      "The hysteresis value of the sensor times 1000 as integer"
              ::= { s64 11 }


	-- sensor65:
            s65id OBJECT-TYPE
              SYNTAX  DisplayString
              ACCESS  read-only
              STATUS  mandatory
              DESCRIPTION
                      "A unique value containing sensortype and serial number."
              ::= { s65 1 }

	    s65value OBJECT-TYPE
              SYNTAX  DisplayString
              ACCESS  read-only
              STATUS  mandatory
              DESCRIPTION
                      "The value of the sensor as String."
              ::= { s65 2 }

	    s65unit OBJECT-TYPE
              SYNTAX  DisplayString
              ACCESS  read-only
              STATUS  mandatory
              DESCRIPTION
                      "The unit of the sensor."
              ::= { s65 3 }

	    s65valueInt OBJECT-TYPE
              SYNTAX  INTEGER
              ACCESS  read-write
              STATUS  mandatory
              DESCRIPTION
                      "The value of the sensor times 1000 as integer"
              ::= { s65 4 }

	    s65name OBJECT-TYPE
              SYNTAX  DisplayString
              ACCESS  read-only
              STATUS  mandatory
              DESCRIPTION
                      "The name of the sensor as String. 
		       This name is set by the user in the SNMP Config Table."
              ::= { s65 5 }

	    s65alarmInt OBJECT-TYPE
              SYNTAX  INTEGER
              ACCESS  read-only
              STATUS  mandatory
              DESCRIPTION
                      "The Sensor Alarm Status range 1..5 as integer"
              ::= { s65 6 }

	    s65LoLimitAlarmInt OBJECT-TYPE
              SYNTAX  INTEGER
              ACCESS  read-only
              STATUS  mandatory
              DESCRIPTION
                      "The lower limit alarm value of the sensor times 1000 as integer"
              ::= { s65 7 }

	    s65LoLimitWarnInt OBJECT-TYPE
              SYNTAX  INTEGER
              ACCESS  read-only
              STATUS  mandatory
              DESCRIPTION
                      "The lower limit warning value of the sensor times 1000 as integer"
              ::= { s65 8 }

	    s65HiLimitWarnInt OBJECT-TYPE
              SYNTAX  INTEGER
              ACCESS  read-only
              STATUS  mandatory
              DESCRIPTION
                      "The upper limit warning value of the sensor times 1000 as integer"
              ::= { s65 9 }

	    s65HiLimitAlarmInt OBJECT-TYPE
              SYNTAX  INTEGER
              ACCESS  read-only
              STATUS  mandatory
              DESCRIPTION
                      "The upper limit alarm value of the sensor times 1000 as integer"
              ::= { s65 10 }

	    s65HysterInt OBJECT-TYPE
              SYNTAX  INTEGER
              ACCESS  read-only
              STATUS  mandatory
              DESCRIPTION
                      "The hysteresis value of the sensor times 1000 as integer"
              ::= { s65 11 }


	-- sensor66:
            s66id OBJECT-TYPE
              SYNTAX  DisplayString
              ACCESS  read-only
              STATUS  mandatory
              DESCRIPTION
                      "A unique value containing sensortype and serial number."
              ::= { s66 1 }

	    s66value OBJECT-TYPE
              SYNTAX  DisplayString
              ACCESS  read-only
              STATUS  mandatory
              DESCRIPTION
                      "The value of the sensor as String."
              ::= { s66 2 }

	    s66unit OBJECT-TYPE
              SYNTAX  DisplayString
              ACCESS  read-only
              STATUS  mandatory
              DESCRIPTION
                      "The unit of the sensor."
              ::= { s66 3 }

	    s66valueInt OBJECT-TYPE
              SYNTAX  INTEGER
              ACCESS  read-write
              STATUS  mandatory
              DESCRIPTION
                      "The value of the sensor times 1000 as integer"
              ::= { s66 4 }

	    s66name OBJECT-TYPE
              SYNTAX  DisplayString
              ACCESS  read-only
              STATUS  mandatory
              DESCRIPTION
                      "The name of the sensor as String. 
		       This name is set by the user in the SNMP Config Table."
              ::= { s66 5 }

	    s66alarmInt OBJECT-TYPE
              SYNTAX  INTEGER
              ACCESS  read-only
              STATUS  mandatory
              DESCRIPTION
                      "The Sensor Alarm Status range 1..5 as integer"
              ::= { s66 6 }

	    s66LoLimitAlarmInt OBJECT-TYPE
              SYNTAX  INTEGER
              ACCESS  read-only
              STATUS  mandatory
              DESCRIPTION
                      "The lower limit alarm value of the sensor times 1000 as integer"
              ::= { s66 7 }

	    s66LoLimitWarnInt OBJECT-TYPE
              SYNTAX  INTEGER
              ACCESS  read-only
              STATUS  mandatory
              DESCRIPTION
                      "The lower limit warning value of the sensor times 1000 as integer"
              ::= { s66 8 }

	    s66HiLimitWarnInt OBJECT-TYPE
              SYNTAX  INTEGER
              ACCESS  read-only
              STATUS  mandatory
              DESCRIPTION
                      "The upper limit warning value of the sensor times 1000 as integer"
              ::= { s66 9 }

	    s66HiLimitAlarmInt OBJECT-TYPE
              SYNTAX  INTEGER
              ACCESS  read-only
              STATUS  mandatory
              DESCRIPTION
                      "The upper limit alarm value of the sensor times 1000 as integer"
              ::= { s66 10 }

	    s66HysterInt OBJECT-TYPE
              SYNTAX  INTEGER
              ACCESS  read-only
              STATUS  mandatory
              DESCRIPTION
                      "The hysteresis value of the sensor times 1000 as integer"
              ::= { s66 11 }


	-- sensor67:
            s67id OBJECT-TYPE
              SYNTAX  DisplayString
              ACCESS  read-only
              STATUS  mandatory
              DESCRIPTION
                      "A unique value containing sensortype and serial number."
              ::= { s67 1 }

	    s67value OBJECT-TYPE
              SYNTAX  DisplayString
              ACCESS  read-only
              STATUS  mandatory
              DESCRIPTION
                      "The value of the sensor as String."
              ::= { s67 2 }

	    s67unit OBJECT-TYPE
              SYNTAX  DisplayString
              ACCESS  read-only
              STATUS  mandatory
              DESCRIPTION
                      "The unit of the sensor."
              ::= { s67 3 }

	    s67valueInt OBJECT-TYPE
              SYNTAX  INTEGER
              ACCESS  read-write
              STATUS  mandatory
              DESCRIPTION
                      "The value of the sensor times 1000 as integer"
              ::= { s67 4 }

	    s67name OBJECT-TYPE
              SYNTAX  DisplayString
              ACCESS  read-only
              STATUS  mandatory
              DESCRIPTION
                      "The name of the sensor as String. 
		       This name is set by the user in the SNMP Config Table."
              ::= { s67 5 }

	    s67alarmInt OBJECT-TYPE
              SYNTAX  INTEGER
              ACCESS  read-only
              STATUS  mandatory
              DESCRIPTION
                      "The Sensor Alarm Status range 1..5 as integer"
              ::= { s67 6 }

	    s67LoLimitAlarmInt OBJECT-TYPE
              SYNTAX  INTEGER
              ACCESS  read-only
              STATUS  mandatory
              DESCRIPTION
                      "The lower limit alarm value of the sensor times 1000 as integer"
              ::= { s67 7 }

	    s67LoLimitWarnInt OBJECT-TYPE
              SYNTAX  INTEGER
              ACCESS  read-only
              STATUS  mandatory
              DESCRIPTION
                      "The lower limit warning value of the sensor times 1000 as integer"
              ::= { s67 8 }

	    s67HiLimitWarnInt OBJECT-TYPE
              SYNTAX  INTEGER
              ACCESS  read-only
              STATUS  mandatory
              DESCRIPTION
                      "The upper limit warning value of the sensor times 1000 as integer"
              ::= { s67 9 }

	    s67HiLimitAlarmInt OBJECT-TYPE
              SYNTAX  INTEGER
              ACCESS  read-only
              STATUS  mandatory
              DESCRIPTION
                      "The upper limit alarm value of the sensor times 1000 as integer"
              ::= { s67 10 }

	    s67HysterInt OBJECT-TYPE
              SYNTAX  INTEGER
              ACCESS  read-only
              STATUS  mandatory
              DESCRIPTION
                      "The hysteresis value of the sensor times 1000 as integer"
              ::= { s67 11 }


	-- sensor68:
            s68id OBJECT-TYPE
              SYNTAX  DisplayString
              ACCESS  read-only
              STATUS  mandatory
              DESCRIPTION
                      "A unique value containing sensortype and serial number."
              ::= { s68 1 }

	    s68value OBJECT-TYPE
              SYNTAX  DisplayString
              ACCESS  read-only
              STATUS  mandatory
              DESCRIPTION
                      "The value of the sensor as String."
              ::= { s68 2 }

	    s68unit OBJECT-TYPE
              SYNTAX  DisplayString
              ACCESS  read-only
              STATUS  mandatory
              DESCRIPTION
                      "The unit of the sensor."
              ::= { s68 3 }

	    s68valueInt OBJECT-TYPE
              SYNTAX  INTEGER
              ACCESS  read-write
              STATUS  mandatory
              DESCRIPTION
                      "The value of the sensor times 1000 as integer"
              ::= { s68 4 }

	    s68name OBJECT-TYPE
              SYNTAX  DisplayString
              ACCESS  read-only
              STATUS  mandatory
              DESCRIPTION
                      "The name of the sensor as String. 
		       This name is set by the user in the SNMP Config Table."
              ::= { s68 5 }

	    s68alarmInt OBJECT-TYPE
              SYNTAX  INTEGER
              ACCESS  read-only
              STATUS  mandatory
              DESCRIPTION
                      "The Sensor Alarm Status range 1..5 as integer"
              ::= { s68 6 }

	    s68LoLimitAlarmInt OBJECT-TYPE
              SYNTAX  INTEGER
              ACCESS  read-only
              STATUS  mandatory
              DESCRIPTION
                      "The lower limit alarm value of the sensor times 1000 as integer"
              ::= { s68 7 }

	    s68LoLimitWarnInt OBJECT-TYPE
              SYNTAX  INTEGER
              ACCESS  read-only
              STATUS  mandatory
              DESCRIPTION
                      "The lower limit warning value of the sensor times 1000 as integer"
              ::= { s68 8 }

	    s68HiLimitWarnInt OBJECT-TYPE
              SYNTAX  INTEGER
              ACCESS  read-only
              STATUS  mandatory
              DESCRIPTION
                      "The upper limit warning value of the sensor times 1000 as integer"
              ::= { s68 9 }

	    s68HiLimitAlarmInt OBJECT-TYPE
              SYNTAX  INTEGER
              ACCESS  read-only
              STATUS  mandatory
              DESCRIPTION
                      "The upper limit alarm value of the sensor times 1000 as integer"
              ::= { s68 10 }

	    s68HysterInt OBJECT-TYPE
              SYNTAX  INTEGER
              ACCESS  read-only
              STATUS  mandatory
              DESCRIPTION
                      "The hysteresis value of the sensor times 1000 as integer"
              ::= { s68 11 }


	-- sensor69:
            s69id OBJECT-TYPE
              SYNTAX  DisplayString
              ACCESS  read-only
              STATUS  mandatory
              DESCRIPTION
                      "A unique value containing sensortype and serial number."
              ::= { s69 1 }

	    s69value OBJECT-TYPE
              SYNTAX  DisplayString
              ACCESS  read-only
              STATUS  mandatory
              DESCRIPTION
                      "The value of the sensor as String."
              ::= { s69 2 }

	    s69unit OBJECT-TYPE
              SYNTAX  DisplayString
              ACCESS  read-only
              STATUS  mandatory
              DESCRIPTION
                      "The unit of the sensor."
              ::= { s69 3 }

	    s69valueInt OBJECT-TYPE
              SYNTAX  INTEGER
              ACCESS  read-write
              STATUS  mandatory
              DESCRIPTION
                      "The value of the sensor times 1000 as integer"
              ::= { s69 4 }

	    s69name OBJECT-TYPE
              SYNTAX  DisplayString
              ACCESS  read-only
              STATUS  mandatory
              DESCRIPTION
                      "The name of the sensor as String. 
		       This name is set by the user in the SNMP Config Table."
              ::= { s69 5 }

	    s69alarmInt OBJECT-TYPE
              SYNTAX  INTEGER
              ACCESS  read-only
              STATUS  mandatory
              DESCRIPTION
                      "The Sensor Alarm Status range 1..5 as integer"
              ::= { s69 6 }

	    s69LoLimitAlarmInt OBJECT-TYPE
              SYNTAX  INTEGER
              ACCESS  read-only
              STATUS  mandatory
              DESCRIPTION
                      "The lower limit alarm value of the sensor times 1000 as integer"
              ::= { s69 7 }

	    s69LoLimitWarnInt OBJECT-TYPE
              SYNTAX  INTEGER
              ACCESS  read-only
              STATUS  mandatory
              DESCRIPTION
                      "The lower limit warning value of the sensor times 1000 as integer"
              ::= { s69 8 }

	    s69HiLimitWarnInt OBJECT-TYPE
              SYNTAX  INTEGER
              ACCESS  read-only
              STATUS  mandatory
              DESCRIPTION
                      "The upper limit warning value of the sensor times 1000 as integer"
              ::= { s69 9 }

	    s69HiLimitAlarmInt OBJECT-TYPE
              SYNTAX  INTEGER
              ACCESS  read-only
              STATUS  mandatory
              DESCRIPTION
                      "The upper limit alarm value of the sensor times 1000 as integer"
              ::= { s69 10 }

	    s69HysterInt OBJECT-TYPE
              SYNTAX  INTEGER
              ACCESS  read-only
              STATUS  mandatory
              DESCRIPTION
                      "The hysteresis value of the sensor times 1000 as integer"
              ::= { s69 11 }


	-- sensor70:
            s70id OBJECT-TYPE
              SYNTAX  DisplayString
              ACCESS  read-only
              STATUS  mandatory
              DESCRIPTION
                      "A unique value containing sensortype and serial number."
              ::= { s70 1 }

	    s70value OBJECT-TYPE
              SYNTAX  DisplayString
              ACCESS  read-only
              STATUS  mandatory
              DESCRIPTION
                      "The value of the sensor as String."
              ::= { s70 2 }

	    s70unit OBJECT-TYPE
              SYNTAX  DisplayString
              ACCESS  read-only
              STATUS  mandatory
              DESCRIPTION
                      "The unit of the sensor."
              ::= { s70 3 }

	    s70valueInt OBJECT-TYPE
              SYNTAX  INTEGER
              ACCESS  read-write
              STATUS  mandatory
              DESCRIPTION
                      "The value of the sensor times 1000 as integer"
              ::= { s70 4 }

	    s70name OBJECT-TYPE
              SYNTAX  DisplayString
              ACCESS  read-only
              STATUS  mandatory
              DESCRIPTION
                      "The name of the sensor as String. 
		       This name is set by the user in the SNMP Config Table."
              ::= { s70 5 }

	    s70alarmInt OBJECT-TYPE
              SYNTAX  INTEGER
              ACCESS  read-only
              STATUS  mandatory
              DESCRIPTION
                      "The Sensor Alarm Status range 1..5 as integer"
              ::= { s70 6 }

	    s70LoLimitAlarmInt OBJECT-TYPE
              SYNTAX  INTEGER
              ACCESS  read-only
              STATUS  mandatory
              DESCRIPTION
                      "The lower limit alarm value of the sensor times 1000 as integer"
              ::= { s70 7 }

	    s70LoLimitWarnInt OBJECT-TYPE
              SYNTAX  INTEGER
              ACCESS  read-only
              STATUS  mandatory
              DESCRIPTION
                      "The lower limit warning value of the sensor times 1000 as integer"
              ::= { s70 8 }

	    s70HiLimitWarnInt OBJECT-TYPE
              SYNTAX  INTEGER
              ACCESS  read-only
              STATUS  mandatory
              DESCRIPTION
                      "The upper limit warning value of the sensor times 1000 as integer"
              ::= { s70 9 }

	    s70HiLimitAlarmInt OBJECT-TYPE
              SYNTAX  INTEGER
              ACCESS  read-only
              STATUS  mandatory
              DESCRIPTION
                      "The upper limit alarm value of the sensor times 1000 as integer"
              ::= { s70 10 }

	    s70HysterInt OBJECT-TYPE
              SYNTAX  INTEGER
              ACCESS  read-only
              STATUS  mandatory
              DESCRIPTION
                      "The hysteresis value of the sensor times 1000 as integer"
              ::= { s70 11 }


  --  71 - 80
	-- sensor71:
            s71id OBJECT-TYPE
              SYNTAX  DisplayString
              ACCESS  read-only
              STATUS  mandatory
              DESCRIPTION
                      "A unique value containing sensortype and serial number."
              ::= { s71 1 }

	    s71value OBJECT-TYPE
              SYNTAX  DisplayString
              ACCESS  read-only
              STATUS  mandatory
              DESCRIPTION
                      "The value of the sensor as String."
              ::= { s71 2 }

	    s71unit OBJECT-TYPE
              SYNTAX  DisplayString
              ACCESS  read-only
              STATUS  mandatory
              DESCRIPTION
                      "The unit of the sensor."
              ::= { s71 3 }

	    s71valueInt OBJECT-TYPE
              SYNTAX  INTEGER
              ACCESS  read-write
              STATUS  mandatory
              DESCRIPTION
                      "The value of the sensor times 1000 as integer"
              ::= { s71 4 }

	    s71name OBJECT-TYPE
              SYNTAX  DisplayString
              ACCESS  read-only
              STATUS  mandatory
              DESCRIPTION
                      "The name of the sensor as String. 
		       This name is set by the user in the SNMP Config Table."
              ::= { s71 5 }

	    s71alarmInt OBJECT-TYPE
              SYNTAX  INTEGER
              ACCESS  read-only
              STATUS  mandatory
              DESCRIPTION
                      "The Sensor Alarm Status range 1..5 as integer"
              ::= { s71 6 }

	    s71LoLimitAlarmInt OBJECT-TYPE
              SYNTAX  INTEGER
              ACCESS  read-only
              STATUS  mandatory
              DESCRIPTION
                      "The lower limit alarm value of the sensor times 1000 as integer"
              ::= { s71 7 }

	    s71LoLimitWarnInt OBJECT-TYPE
              SYNTAX  INTEGER
              ACCESS  read-only
              STATUS  mandatory
              DESCRIPTION
                      "The lower limit warning value of the sensor times 1000 as integer"
              ::= { s71 8 }

	    s71HiLimitWarnInt OBJECT-TYPE
              SYNTAX  INTEGER
              ACCESS  read-only
              STATUS  mandatory
              DESCRIPTION
                      "The upper limit warning value of the sensor times 1000 as integer"
              ::= { s71 9 }

	    s71HiLimitAlarmInt OBJECT-TYPE
              SYNTAX  INTEGER
              ACCESS  read-only
              STATUS  mandatory
              DESCRIPTION
                      "The upper limit alarm value of the sensor times 1000 as integer"
              ::= { s71 10 }

	    s71HysterInt OBJECT-TYPE
              SYNTAX  INTEGER
              ACCESS  read-only
              STATUS  mandatory
              DESCRIPTION
                      "The hysteresis value of the sensor times 1000 as integer"
              ::= { s71 11 }


	-- sensor72:
            s72id OBJECT-TYPE
              SYNTAX  DisplayString
              ACCESS  read-only
              STATUS  mandatory
              DESCRIPTION
                      "A unique value containing sensortype and serial number."
              ::= { s72 1 }

	    s72value OBJECT-TYPE
              SYNTAX  DisplayString
              ACCESS  read-only
              STATUS  mandatory
              DESCRIPTION
                      "The value of the sensor as String."
              ::= { s72 2 }

	    s72unit OBJECT-TYPE
              SYNTAX  DisplayString
              ACCESS  read-only
              STATUS  mandatory
              DESCRIPTION
                      "The unit of the sensor."
              ::= { s72 3 }

	    s72valueInt OBJECT-TYPE
              SYNTAX  INTEGER
              ACCESS  read-write
              STATUS  mandatory
              DESCRIPTION
                      "The value of the sensor times 1000 as integer"
              ::= { s72 4 }

	    s72name OBJECT-TYPE
              SYNTAX  DisplayString
              ACCESS  read-only
              STATUS  mandatory
              DESCRIPTION
                      "The name of the sensor as String. 
		       This name is set by the user in the SNMP Config Table."
              ::= { s72 5 }

	    s72alarmInt OBJECT-TYPE
              SYNTAX  INTEGER
              ACCESS  read-only
              STATUS  mandatory
              DESCRIPTION
                      "The Sensor Alarm Status range 1..5 as integer"
              ::= { s72 6 }

	    s72LoLimitAlarmInt OBJECT-TYPE
              SYNTAX  INTEGER
              ACCESS  read-only
              STATUS  mandatory
              DESCRIPTION
                      "The lower limit alarm value of the sensor times 1000 as integer"
              ::= { s72 7 }

	    s72LoLimitWarnInt OBJECT-TYPE
              SYNTAX  INTEGER
              ACCESS  read-only
              STATUS  mandatory
              DESCRIPTION
                      "The lower limit warning value of the sensor times 1000 as integer"
              ::= { s72 8 }

	    s72HiLimitWarnInt OBJECT-TYPE
              SYNTAX  INTEGER
              ACCESS  read-only
              STATUS  mandatory
              DESCRIPTION
                      "The upper limit warning value of the sensor times 1000 as integer"
              ::= { s72 9 }

	    s72HiLimitAlarmInt OBJECT-TYPE
              SYNTAX  INTEGER
              ACCESS  read-only
              STATUS  mandatory
              DESCRIPTION
                      "The upper limit alarm value of the sensor times 1000 as integer"
              ::= { s72 10 }

	    s72HysterInt OBJECT-TYPE
              SYNTAX  INTEGER
              ACCESS  read-only
              STATUS  mandatory
              DESCRIPTION
                      "The hysteresis value of the sensor times 1000 as integer"
              ::= { s72 11 }


	-- sensor73:
            s73id OBJECT-TYPE
              SYNTAX  DisplayString
              ACCESS  read-only
              STATUS  mandatory
              DESCRIPTION
                      "A unique value containing sensortype and serial number."
              ::= { s73 1 }

	    s73value OBJECT-TYPE
              SYNTAX  DisplayString
              ACCESS  read-only
              STATUS  mandatory
              DESCRIPTION
                      "The value of the sensor as String."
              ::= { s73 2 }

	    s73unit OBJECT-TYPE
              SYNTAX  DisplayString
              ACCESS  read-only
              STATUS  mandatory
              DESCRIPTION
                      "The unit of the sensor."
              ::= { s73 3 }

	    s73valueInt OBJECT-TYPE
              SYNTAX  INTEGER
              ACCESS  read-write
              STATUS  mandatory
              DESCRIPTION
                      "The value of the sensor times 1000 as integer"
              ::= { s73 4 }

	    s73name OBJECT-TYPE
              SYNTAX  DisplayString
              ACCESS  read-only
              STATUS  mandatory
              DESCRIPTION
                      "The name of the sensor as String. 
		       This name is set by the user in the SNMP Config Table."
              ::= { s73 5 }

	    s73alarmInt OBJECT-TYPE
              SYNTAX  INTEGER
              ACCESS  read-only
              STATUS  mandatory
              DESCRIPTION
                      "The Sensor Alarm Status range 1..5 as integer"
              ::= { s73 6 }

	    s73LoLimitAlarmInt OBJECT-TYPE
              SYNTAX  INTEGER
              ACCESS  read-only
              STATUS  mandatory
              DESCRIPTION
                      "The lower limit alarm value of the sensor times 1000 as integer"
              ::= { s73 7 }

	    s73LoLimitWarnInt OBJECT-TYPE
              SYNTAX  INTEGER
              ACCESS  read-only
              STATUS  mandatory
              DESCRIPTION
                      "The lower limit warning value of the sensor times 1000 as integer"
              ::= { s73 8 }

	    s73HiLimitWarnInt OBJECT-TYPE
              SYNTAX  INTEGER
              ACCESS  read-only
              STATUS  mandatory
              DESCRIPTION
                      "The upper limit warning value of the sensor times 1000 as integer"
              ::= { s73 9 }

	    s73HiLimitAlarmInt OBJECT-TYPE
              SYNTAX  INTEGER
              ACCESS  read-only
              STATUS  mandatory
              DESCRIPTION
                      "The upper limit alarm value of the sensor times 1000 as integer"
              ::= { s73 10 }

	    s73HysterInt OBJECT-TYPE
              SYNTAX  INTEGER
              ACCESS  read-only
              STATUS  mandatory
              DESCRIPTION
                      "The hysteresis value of the sensor times 1000 as integer"
              ::= { s73 11 }


	-- sensor74:
            s74id OBJECT-TYPE
              SYNTAX  DisplayString
              ACCESS  read-only
              STATUS  mandatory
              DESCRIPTION
                      "A unique value containing sensortype and serial number."
              ::= { s74 1 }

	    s74value OBJECT-TYPE
              SYNTAX  DisplayString
              ACCESS  read-only
              STATUS  mandatory
              DESCRIPTION
                      "The value of the sensor as String."
              ::= { s74 2 }

	    s74unit OBJECT-TYPE
              SYNTAX  DisplayString
              ACCESS  read-only
              STATUS  mandatory
              DESCRIPTION
                      "The unit of the sensor."
              ::= { s74 3 }

	    s74valueInt OBJECT-TYPE
              SYNTAX  INTEGER
              ACCESS  read-write
              STATUS  mandatory
              DESCRIPTION
                      "The value of the sensor times 1000 as integer"
              ::= { s74 4 }

	    s74name OBJECT-TYPE
              SYNTAX  DisplayString
              ACCESS  read-only
              STATUS  mandatory
              DESCRIPTION
                      "The name of the sensor as String. 
		       This name is set by the user in the SNMP Config Table."
              ::= { s74 5 }

	    s74alarmInt OBJECT-TYPE
              SYNTAX  INTEGER
              ACCESS  read-only
              STATUS  mandatory
              DESCRIPTION
                      "The Sensor Alarm Status range 1..5 as integer"
              ::= { s74 6 }

	    s74LoLimitAlarmInt OBJECT-TYPE
              SYNTAX  INTEGER
              ACCESS  read-only
              STATUS  mandatory
              DESCRIPTION
                      "The lower limit alarm value of the sensor times 1000 as integer"
              ::= { s74 7 }

	    s74LoLimitWarnInt OBJECT-TYPE
              SYNTAX  INTEGER
              ACCESS  read-only
              STATUS  mandatory
              DESCRIPTION
                      "The lower limit warning value of the sensor times 1000 as integer"
              ::= { s74 8 }

	    s74HiLimitWarnInt OBJECT-TYPE
              SYNTAX  INTEGER
              ACCESS  read-only
              STATUS  mandatory
              DESCRIPTION
                      "The upper limit warning value of the sensor times 1000 as integer"
              ::= { s74 9 }

	    s74HiLimitAlarmInt OBJECT-TYPE
              SYNTAX  INTEGER
              ACCESS  read-only
              STATUS  mandatory
              DESCRIPTION
                      "The upper limit alarm value of the sensor times 1000 as integer"
              ::= { s74 10 }

	    s74HysterInt OBJECT-TYPE
              SYNTAX  INTEGER
              ACCESS  read-only
              STATUS  mandatory
              DESCRIPTION
                      "The hysteresis value of the sensor times 1000 as integer"
              ::= { s74 11 }


	-- sensor75:
            s75id OBJECT-TYPE
              SYNTAX  DisplayString
              ACCESS  read-only
              STATUS  mandatory
              DESCRIPTION
                      "A unique value containing sensortype and serial number."
              ::= { s75 1 }

	    s75value OBJECT-TYPE
              SYNTAX  DisplayString
              ACCESS  read-only
              STATUS  mandatory
              DESCRIPTION
                      "The value of the sensor as String."
              ::= { s75 2 }

	    s75unit OBJECT-TYPE
              SYNTAX  DisplayString
              ACCESS  read-only
              STATUS  mandatory
              DESCRIPTION
                      "The unit of the sensor."
              ::= { s75 3 }

	    s75valueInt OBJECT-TYPE
              SYNTAX  INTEGER
              ACCESS  read-write
              STATUS  mandatory
              DESCRIPTION
                      "The value of the sensor times 1000 as integer"
              ::= { s75 4 }

	    s75name OBJECT-TYPE
              SYNTAX  DisplayString
              ACCESS  read-only
              STATUS  mandatory
              DESCRIPTION
                      "The name of the sensor as String. 
		       This name is set by the user in the SNMP Config Table."
              ::= { s75 5 }

	    s75alarmInt OBJECT-TYPE
              SYNTAX  INTEGER
              ACCESS  read-only
              STATUS  mandatory
              DESCRIPTION
                      "The Sensor Alarm Status range 1..5 as integer"
              ::= { s75 6 }

	    s75LoLimitAlarmInt OBJECT-TYPE
              SYNTAX  INTEGER
              ACCESS  read-only
              STATUS  mandatory
              DESCRIPTION
                      "The lower limit alarm value of the sensor times 1000 as integer"
              ::= { s75 7 }

	    s75LoLimitWarnInt OBJECT-TYPE
              SYNTAX  INTEGER
              ACCESS  read-only
              STATUS  mandatory
              DESCRIPTION
                      "The lower limit warning value of the sensor times 1000 as integer"
              ::= { s75 8 }

	    s75HiLimitWarnInt OBJECT-TYPE
              SYNTAX  INTEGER
              ACCESS  read-only
              STATUS  mandatory
              DESCRIPTION
                      "The upper limit warning value of the sensor times 1000 as integer"
              ::= { s75 9 }

	    s75HiLimitAlarmInt OBJECT-TYPE
              SYNTAX  INTEGER
              ACCESS  read-only
              STATUS  mandatory
              DESCRIPTION
                      "The upper limit alarm value of the sensor times 1000 as integer"
              ::= { s75 10 }

	    s75HysterInt OBJECT-TYPE
              SYNTAX  INTEGER
              ACCESS  read-only
              STATUS  mandatory
              DESCRIPTION
                      "The hysteresis value of the sensor times 1000 as integer"
              ::= { s75 11 }


	-- sensor76:
            s76id OBJECT-TYPE
              SYNTAX  DisplayString
              ACCESS  read-only
              STATUS  mandatory
              DESCRIPTION
                      "A unique value containing sensortype and serial number."
              ::= { s76 1 }

	    s76value OBJECT-TYPE
              SYNTAX  DisplayString
              ACCESS  read-only
              STATUS  mandatory
              DESCRIPTION
                      "The value of the sensor as String."
              ::= { s76 2 }

	    s76unit OBJECT-TYPE
              SYNTAX  DisplayString
              ACCESS  read-only
              STATUS  mandatory
              DESCRIPTION
                      "The unit of the sensor."
              ::= { s76 3 }

	    s76valueInt OBJECT-TYPE
              SYNTAX  INTEGER
              ACCESS  read-write
              STATUS  mandatory
              DESCRIPTION
                      "The value of the sensor times 1000 as integer"
              ::= { s76 4 }

	    s76name OBJECT-TYPE
              SYNTAX  DisplayString
              ACCESS  read-only
              STATUS  mandatory
              DESCRIPTION
                      "The name of the sensor as String. 
		       This name is set by the user in the SNMP Config Table."
              ::= { s76 5 }

	    s76alarmInt OBJECT-TYPE
              SYNTAX  INTEGER
              ACCESS  read-only
              STATUS  mandatory
              DESCRIPTION
                      "The Sensor Alarm Status range 1..5 as integer"
              ::= { s76 6 }

	    s76LoLimitAlarmInt OBJECT-TYPE
              SYNTAX  INTEGER
              ACCESS  read-only
              STATUS  mandatory
              DESCRIPTION
                      "The lower limit alarm value of the sensor times 1000 as integer"
              ::= { s76 7 }

	    s76LoLimitWarnInt OBJECT-TYPE
              SYNTAX  INTEGER
              ACCESS  read-only
              STATUS  mandatory
              DESCRIPTION
                      "The lower limit warning value of the sensor times 1000 as integer"
              ::= { s76 8 }

	    s76HiLimitWarnInt OBJECT-TYPE
              SYNTAX  INTEGER
              ACCESS  read-only
              STATUS  mandatory
              DESCRIPTION
                      "The upper limit warning value of the sensor times 1000 as integer"
              ::= { s76 9 }

	    s76HiLimitAlarmInt OBJECT-TYPE
              SYNTAX  INTEGER
              ACCESS  read-only
              STATUS  mandatory
              DESCRIPTION
                      "The upper limit alarm value of the sensor times 1000 as integer"
              ::= { s76 10 }

	    s76HysterInt OBJECT-TYPE
              SYNTAX  INTEGER
              ACCESS  read-only
              STATUS  mandatory
              DESCRIPTION
                      "The hysteresis value of the sensor times 1000 as integer"
              ::= { s76 11 }


	-- sensor77:
            s77id OBJECT-TYPE
              SYNTAX  DisplayString
              ACCESS  read-only
              STATUS  mandatory
              DESCRIPTION
                      "A unique value containing sensortype and serial number."
              ::= { s77 1 }

	    s77value OBJECT-TYPE
              SYNTAX  DisplayString
              ACCESS  read-only
              STATUS  mandatory
              DESCRIPTION
                      "The value of the sensor as String."
              ::= { s77 2 }

	    s77unit OBJECT-TYPE
              SYNTAX  DisplayString
              ACCESS  read-only
              STATUS  mandatory
              DESCRIPTION
                      "The unit of the sensor."
              ::= { s77 3 }

	    s77valueInt OBJECT-TYPE
              SYNTAX  INTEGER
              ACCESS  read-write
              STATUS  mandatory
              DESCRIPTION
                      "The value of the sensor times 1000 as integer"
              ::= { s77 4 }

	    s77name OBJECT-TYPE
              SYNTAX  DisplayString
              ACCESS  read-only
              STATUS  mandatory
              DESCRIPTION
                      "The name of the sensor as String. 
		       This name is set by the user in the SNMP Config Table."
              ::= { s77 5 }

	    s77alarmInt OBJECT-TYPE
              SYNTAX  INTEGER
              ACCESS  read-only
              STATUS  mandatory
              DESCRIPTION
                      "The Sensor Alarm Status range 1..5 as integer"
              ::= { s77 6 }

	    s77LoLimitAlarmInt OBJECT-TYPE
              SYNTAX  INTEGER
              ACCESS  read-only
              STATUS  mandatory
              DESCRIPTION
                      "The lower limit alarm value of the sensor times 1000 as integer"
              ::= { s77 7 }

	    s77LoLimitWarnInt OBJECT-TYPE
              SYNTAX  INTEGER
              ACCESS  read-only
              STATUS  mandatory
              DESCRIPTION
                      "The lower limit warning value of the sensor times 1000 as integer"
              ::= { s77 8 }

	    s77HiLimitWarnInt OBJECT-TYPE
              SYNTAX  INTEGER
              ACCESS  read-only
              STATUS  mandatory
              DESCRIPTION
                      "The upper limit warning value of the sensor times 1000 as integer"
              ::= { s77 9 }

	    s77HiLimitAlarmInt OBJECT-TYPE
              SYNTAX  INTEGER
              ACCESS  read-only
              STATUS  mandatory
              DESCRIPTION
                      "The upper limit alarm value of the sensor times 1000 as integer"
              ::= { s77 10 }

	    s77HysterInt OBJECT-TYPE
              SYNTAX  INTEGER
              ACCESS  read-only
              STATUS  mandatory
              DESCRIPTION
                      "The hysteresis value of the sensor times 1000 as integer"
              ::= { s77 11 }


	-- sensor78:
            s78id OBJECT-TYPE
              SYNTAX  DisplayString
              ACCESS  read-only
              STATUS  mandatory
              DESCRIPTION
                      "A unique value containing sensortype and serial number."
              ::= { s78 1 }

	    s78value OBJECT-TYPE
              SYNTAX  DisplayString
              ACCESS  read-only
              STATUS  mandatory
              DESCRIPTION
                      "The value of the sensor as String."
              ::= { s78 2 }

	    s78unit OBJECT-TYPE
              SYNTAX  DisplayString
              ACCESS  read-only
              STATUS  mandatory
              DESCRIPTION
                      "The unit of the sensor."
              ::= { s78 3 }

	    s78valueInt OBJECT-TYPE
              SYNTAX  INTEGER
              ACCESS  read-write
              STATUS  mandatory
              DESCRIPTION
                      "The value of the sensor times 1000 as integer"
              ::= { s78 4 }

	    s78name OBJECT-TYPE
              SYNTAX  DisplayString
              ACCESS  read-only
              STATUS  mandatory
              DESCRIPTION
                      "The name of the sensor as String. 
		       This name is set by the user in the SNMP Config Table."
              ::= { s78 5 }

	    s78alarmInt OBJECT-TYPE
              SYNTAX  INTEGER
              ACCESS  read-only
              STATUS  mandatory
              DESCRIPTION
                      "The Sensor Alarm Status range 1..5 as integer"
              ::= { s78 6 }

	    s78LoLimitAlarmInt OBJECT-TYPE
              SYNTAX  INTEGER
              ACCESS  read-only
              STATUS  mandatory
              DESCRIPTION
                      "The lower limit alarm value of the sensor times 1000 as integer"
              ::= { s78 7 }

	    s78LoLimitWarnInt OBJECT-TYPE
              SYNTAX  INTEGER
              ACCESS  read-only
              STATUS  mandatory
              DESCRIPTION
                      "The lower limit warning value of the sensor times 1000 as integer"
              ::= { s78 8 }

	    s78HiLimitWarnInt OBJECT-TYPE
              SYNTAX  INTEGER
              ACCESS  read-only
              STATUS  mandatory
              DESCRIPTION
                      "The upper limit warning value of the sensor times 1000 as integer"
              ::= { s78 9 }

	    s78HiLimitAlarmInt OBJECT-TYPE
              SYNTAX  INTEGER
              ACCESS  read-only
              STATUS  mandatory
              DESCRIPTION
                      "The upper limit alarm value of the sensor times 1000 as integer"
              ::= { s78 10 }

	    s78HysterInt OBJECT-TYPE
              SYNTAX  INTEGER
              ACCESS  read-only
              STATUS  mandatory
              DESCRIPTION
                      "The hysteresis value of the sensor times 1000 as integer"
              ::= { s78 11 }


	-- sensor79:
            s79id OBJECT-TYPE
              SYNTAX  DisplayString
              ACCESS  read-only
              STATUS  mandatory
              DESCRIPTION
                      "A unique value containing sensortype and serial number."
              ::= { s79 1 }

	    s79value OBJECT-TYPE
              SYNTAX  DisplayString
              ACCESS  read-only
              STATUS  mandatory
              DESCRIPTION
                      "The value of the sensor as String."
              ::= { s79 2 }

	    s79unit OBJECT-TYPE
              SYNTAX  DisplayString
              ACCESS  read-only
              STATUS  mandatory
              DESCRIPTION
                      "The unit of the sensor."
              ::= { s79 3 }

	    s79valueInt OBJECT-TYPE
              SYNTAX  INTEGER
              ACCESS  read-write
              STATUS  mandatory
              DESCRIPTION
                      "The value of the sensor times 1000 as integer"
              ::= { s79 4 }

	    s79name OBJECT-TYPE
              SYNTAX  DisplayString
              ACCESS  read-only
              STATUS  mandatory
              DESCRIPTION
                      "The name of the sensor as String. 
		       This name is set by the user in the SNMP Config Table."
              ::= { s79 5 }

	    s79alarmInt OBJECT-TYPE
              SYNTAX  INTEGER
              ACCESS  read-only
              STATUS  mandatory
              DESCRIPTION
                      "The Sensor Alarm Status range 1..5 as integer"
              ::= { s79 6 }

	    s79LoLimitAlarmInt OBJECT-TYPE
              SYNTAX  INTEGER
              ACCESS  read-only
              STATUS  mandatory
              DESCRIPTION
                      "The lower limit alarm value of the sensor times 1000 as integer"
              ::= { s79 7 }

	    s79LoLimitWarnInt OBJECT-TYPE
              SYNTAX  INTEGER
              ACCESS  read-only
              STATUS  mandatory
              DESCRIPTION
                      "The lower limit warning value of the sensor times 1000 as integer"
              ::= { s79 8 }

	    s79HiLimitWarnInt OBJECT-TYPE
              SYNTAX  INTEGER
              ACCESS  read-only
              STATUS  mandatory
              DESCRIPTION
                      "The upper limit warning value of the sensor times 1000 as integer"
              ::= { s79 9 }

	    s79HiLimitAlarmInt OBJECT-TYPE
              SYNTAX  INTEGER
              ACCESS  read-only
              STATUS  mandatory
              DESCRIPTION
                      "The upper limit alarm value of the sensor times 1000 as integer"
              ::= { s79 10 }

	    s79HysterInt OBJECT-TYPE
              SYNTAX  INTEGER
              ACCESS  read-only
              STATUS  mandatory
              DESCRIPTION
                      "The hysteresis value of the sensor times 1000 as integer"
              ::= { s79 11 }


	-- sensor80:
            s80id OBJECT-TYPE
              SYNTAX  DisplayString
              ACCESS  read-only
              STATUS  mandatory
              DESCRIPTION
                      "A unique value containing sensortype and serial number."
              ::= { s80 1 }

	    s80value OBJECT-TYPE
              SYNTAX  DisplayString
              ACCESS  read-only
              STATUS  mandatory
              DESCRIPTION
                      "The value of the sensor as String."
              ::= { s80 2 }

	    s80unit OBJECT-TYPE
              SYNTAX  DisplayString
              ACCESS  read-only
              STATUS  mandatory
              DESCRIPTION
                      "The unit of the sensor."
              ::= { s80 3 }

	    s80valueInt OBJECT-TYPE
              SYNTAX  INTEGER
              ACCESS  read-write
              STATUS  mandatory
              DESCRIPTION
                      "The value of the sensor times 1000 as integer"
              ::= { s80 4 }

	    s80name OBJECT-TYPE
              SYNTAX  DisplayString
              ACCESS  read-only
              STATUS  mandatory
              DESCRIPTION
                      "The name of the sensor as String. 
		       This name is set by the user in the SNMP Config Table."
              ::= { s80 5 }

	    s80alarmInt OBJECT-TYPE
              SYNTAX  INTEGER
              ACCESS  read-only
              STATUS  mandatory
              DESCRIPTION
                      "The Sensor Alarm Status range 1..5 as integer"
              ::= { s80 6 }

	    s80LoLimitAlarmInt OBJECT-TYPE
              SYNTAX  INTEGER
              ACCESS  read-only
              STATUS  mandatory
              DESCRIPTION
                      "The lower limit alarm value of the sensor times 1000 as integer"
              ::= { s80 7 }

	    s80LoLimitWarnInt OBJECT-TYPE
              SYNTAX  INTEGER
              ACCESS  read-only
              STATUS  mandatory
              DESCRIPTION
                      "The lower limit warning value of the sensor times 1000 as integer"
              ::= { s80 8 }

	    s80HiLimitWarnInt OBJECT-TYPE
              SYNTAX  INTEGER
              ACCESS  read-only
              STATUS  mandatory
              DESCRIPTION
                      "The upper limit warning value of the sensor times 1000 as integer"
              ::= { s80 9 }

	    s80HiLimitAlarmInt OBJECT-TYPE
              SYNTAX  INTEGER
              ACCESS  read-only
              STATUS  mandatory
              DESCRIPTION
                      "The upper limit alarm value of the sensor times 1000 as integer"
              ::= { s80 10 }

	    s80HysterInt OBJECT-TYPE
              SYNTAX  INTEGER
              ACCESS  read-only
              STATUS  mandatory
              DESCRIPTION
                      "The hysteresis value of the sensor times 1000 as integer"
              ::= { s80 11 }


  --  81 - 90
	-- sensor81:
            s81id OBJECT-TYPE
              SYNTAX  DisplayString
              ACCESS  read-only
              STATUS  mandatory
              DESCRIPTION
                      "A unique value containing sensortype and serial number."
              ::= { s81 1 }

	    s81value OBJECT-TYPE
              SYNTAX  DisplayString
              ACCESS  read-only
              STATUS  mandatory
              DESCRIPTION
                      "The value of the sensor as String."
              ::= { s81 2 }

	    s81unit OBJECT-TYPE
              SYNTAX  DisplayString
              ACCESS  read-only
              STATUS  mandatory
              DESCRIPTION
                      "The unit of the sensor."
              ::= { s81 3 }

	    s81valueInt OBJECT-TYPE
              SYNTAX  INTEGER
              ACCESS  read-write
              STATUS  mandatory
              DESCRIPTION
                      "The value of the sensor times 1000 as integer"
              ::= { s81 4 }

	    s81name OBJECT-TYPE
              SYNTAX  DisplayString
              ACCESS  read-only
              STATUS  mandatory
              DESCRIPTION
                      "The name of the sensor as String. 
		       This name is set by the user in the SNMP Config Table."
              ::= { s81 5 }

	    s81alarmInt OBJECT-TYPE
              SYNTAX  INTEGER
              ACCESS  read-only
              STATUS  mandatory
              DESCRIPTION
                      "The Sensor Alarm Status range 1..5 as integer"
              ::= { s81 6 }

	    s81LoLimitAlarmInt OBJECT-TYPE
              SYNTAX  INTEGER
              ACCESS  read-only
              STATUS  mandatory
              DESCRIPTION
                      "The lower limit alarm value of the sensor times 1000 as integer"
              ::= { s81 7 }

	    s81LoLimitWarnInt OBJECT-TYPE
              SYNTAX  INTEGER
              ACCESS  read-only
              STATUS  mandatory
              DESCRIPTION
                      "The lower limit warning value of the sensor times 1000 as integer"
              ::= { s81 8 }

	    s81HiLimitWarnInt OBJECT-TYPE
              SYNTAX  INTEGER
              ACCESS  read-only
              STATUS  mandatory
              DESCRIPTION
                      "The upper limit warning value of the sensor times 1000 as integer"
              ::= { s81 9 }

	    s81HiLimitAlarmInt OBJECT-TYPE
              SYNTAX  INTEGER
              ACCESS  read-only
              STATUS  mandatory
              DESCRIPTION
                      "The upper limit alarm value of the sensor times 1000 as integer"
              ::= { s81 10 }

	    s81HysterInt OBJECT-TYPE
              SYNTAX  INTEGER
              ACCESS  read-only
              STATUS  mandatory
              DESCRIPTION
                      "The hysteresis value of the sensor times 1000 as integer"
              ::= { s81 11 }


	-- sensor82:
            s82id OBJECT-TYPE
              SYNTAX  DisplayString
              ACCESS  read-only
              STATUS  mandatory
              DESCRIPTION
                      "A unique value containing sensortype and serial number."
              ::= { s82 1 }

	    s82value OBJECT-TYPE
              SYNTAX  DisplayString
              ACCESS  read-only
              STATUS  mandatory
              DESCRIPTION
                      "The value of the sensor as String."
              ::= { s82 2 }

	    s82unit OBJECT-TYPE
              SYNTAX  DisplayString
              ACCESS  read-only
              STATUS  mandatory
              DESCRIPTION
                      "The unit of the sensor."
              ::= { s82 3 }

	    s82valueInt OBJECT-TYPE
              SYNTAX  INTEGER
              ACCESS  read-write
              STATUS  mandatory
              DESCRIPTION
                      "The value of the sensor times 1000 as integer"
              ::= { s82 4 }

	    s82name OBJECT-TYPE
              SYNTAX  DisplayString
              ACCESS  read-only
              STATUS  mandatory
              DESCRIPTION
                      "The name of the sensor as String. 
		       This name is set by the user in the SNMP Config Table."
              ::= { s82 5 }

	    s82alarmInt OBJECT-TYPE
              SYNTAX  INTEGER
              ACCESS  read-only
              STATUS  mandatory
              DESCRIPTION
                      "The Sensor Alarm Status range 1..5 as integer"
              ::= { s82 6 }

	    s82LoLimitAlarmInt OBJECT-TYPE
              SYNTAX  INTEGER
              ACCESS  read-only
              STATUS  mandatory
              DESCRIPTION
                      "The lower limit alarm value of the sensor times 1000 as integer"
              ::= { s82 7 }

	    s82LoLimitWarnInt OBJECT-TYPE
              SYNTAX  INTEGER
              ACCESS  read-only
              STATUS  mandatory
              DESCRIPTION
                      "The lower limit warning value of the sensor times 1000 as integer"
              ::= { s82 8 }

	    s82HiLimitWarnInt OBJECT-TYPE
              SYNTAX  INTEGER
              ACCESS  read-only
              STATUS  mandatory
              DESCRIPTION
                      "The upper limit warning value of the sensor times 1000 as integer"
              ::= { s82 9 }

	    s82HiLimitAlarmInt OBJECT-TYPE
              SYNTAX  INTEGER
              ACCESS  read-only
              STATUS  mandatory
              DESCRIPTION
                      "The upper limit alarm value of the sensor times 1000 as integer"
              ::= { s82 10 }

	    s82HysterInt OBJECT-TYPE
              SYNTAX  INTEGER
              ACCESS  read-only
              STATUS  mandatory
              DESCRIPTION
                      "The hysteresis value of the sensor times 1000 as integer"
              ::= { s82 11 }


	-- sensor83:
            s83id OBJECT-TYPE
              SYNTAX  DisplayString
              ACCESS  read-only
              STATUS  mandatory
              DESCRIPTION
                      "A unique value containing sensortype and serial number."
              ::= { s83 1 }

	    s83value OBJECT-TYPE
              SYNTAX  DisplayString
              ACCESS  read-only
              STATUS  mandatory
              DESCRIPTION
                      "The value of the sensor as String."
              ::= { s83 2 }

	    s83unit OBJECT-TYPE
              SYNTAX  DisplayString
              ACCESS  read-only
              STATUS  mandatory
              DESCRIPTION
                      "The unit of the sensor."
              ::= { s83 3 }

	    s83valueInt OBJECT-TYPE
              SYNTAX  INTEGER
              ACCESS  read-write
              STATUS  mandatory
              DESCRIPTION
                      "The value of the sensor times 1000 as integer"
              ::= { s83 4 }

	    s83name OBJECT-TYPE
              SYNTAX  DisplayString
              ACCESS  read-only
              STATUS  mandatory
              DESCRIPTION
                      "The name of the sensor as String. 
		       This name is set by the user in the SNMP Config Table."
              ::= { s83 5 }

	    s83alarmInt OBJECT-TYPE
              SYNTAX  INTEGER
              ACCESS  read-only
              STATUS  mandatory
              DESCRIPTION
                      "The Sensor Alarm Status range 1..5 as integer"
              ::= { s83 6 }

	    s83LoLimitAlarmInt OBJECT-TYPE
              SYNTAX  INTEGER
              ACCESS  read-only
              STATUS  mandatory
              DESCRIPTION
                      "The lower limit alarm value of the sensor times 1000 as integer"
              ::= { s83 7 }

	    s83LoLimitWarnInt OBJECT-TYPE
              SYNTAX  INTEGER
              ACCESS  read-only
              STATUS  mandatory
              DESCRIPTION
                      "The lower limit warning value of the sensor times 1000 as integer"
              ::= { s83 8 }

	    s83HiLimitWarnInt OBJECT-TYPE
              SYNTAX  INTEGER
              ACCESS  read-only
              STATUS  mandatory
              DESCRIPTION
                      "The upper limit warning value of the sensor times 1000 as integer"
              ::= { s83 9 }

	    s83HiLimitAlarmInt OBJECT-TYPE
              SYNTAX  INTEGER
              ACCESS  read-only
              STATUS  mandatory
              DESCRIPTION
                      "The upper limit alarm value of the sensor times 1000 as integer"
              ::= { s83 10 }

	    s83HysterInt OBJECT-TYPE
              SYNTAX  INTEGER
              ACCESS  read-only
              STATUS  mandatory
              DESCRIPTION
                      "The hysteresis value of the sensor times 1000 as integer"
              ::= { s83 11 }


	-- sensor84:
            s84id OBJECT-TYPE
              SYNTAX  DisplayString
              ACCESS  read-only
              STATUS  mandatory
              DESCRIPTION
                      "A unique value containing sensortype and serial number."
              ::= { s84 1 }

	    s84value OBJECT-TYPE
              SYNTAX  DisplayString
              ACCESS  read-only
              STATUS  mandatory
              DESCRIPTION
                      "The value of the sensor as String."
              ::= { s84 2 }

	    s84unit OBJECT-TYPE
              SYNTAX  DisplayString
              ACCESS  read-only
              STATUS  mandatory
              DESCRIPTION
                      "The unit of the sensor."
              ::= { s84 3 }

	    s84valueInt OBJECT-TYPE
              SYNTAX  INTEGER
              ACCESS  read-write
              STATUS  mandatory
              DESCRIPTION
                      "The value of the sensor times 1000 as integer"
              ::= { s84 4 }

	    s84name OBJECT-TYPE
              SYNTAX  DisplayString
              ACCESS  read-only
              STATUS  mandatory
              DESCRIPTION
                      "The name of the sensor as String. 
		       This name is set by the user in the SNMP Config Table."
              ::= { s84 5 }

	    s84alarmInt OBJECT-TYPE
              SYNTAX  INTEGER
              ACCESS  read-only
              STATUS  mandatory
              DESCRIPTION
                      "The Sensor Alarm Status range 1..5 as integer"
              ::= { s84 6 }

	    s84LoLimitAlarmInt OBJECT-TYPE
              SYNTAX  INTEGER
              ACCESS  read-only
              STATUS  mandatory
              DESCRIPTION
                      "The lower limit alarm value of the sensor times 1000 as integer"
              ::= { s84 7 }

	    s84LoLimitWarnInt OBJECT-TYPE
              SYNTAX  INTEGER
              ACCESS  read-only
              STATUS  mandatory
              DESCRIPTION
                      "The lower limit warning value of the sensor times 1000 as integer"
              ::= { s84 8 }

	    s84HiLimitWarnInt OBJECT-TYPE
              SYNTAX  INTEGER
              ACCESS  read-only
              STATUS  mandatory
              DESCRIPTION
                      "The upper limit warning value of the sensor times 1000 as integer"
              ::= { s84 9 }

	    s84HiLimitAlarmInt OBJECT-TYPE
              SYNTAX  INTEGER
              ACCESS  read-only
              STATUS  mandatory
              DESCRIPTION
                      "The upper limit alarm value of the sensor times 1000 as integer"
              ::= { s84 10 }

	    s84HysterInt OBJECT-TYPE
              SYNTAX  INTEGER
              ACCESS  read-only
              STATUS  mandatory
              DESCRIPTION
                      "The hysteresis value of the sensor times 1000 as integer"
              ::= { s84 11 }


	-- sensor85:
            s85id OBJECT-TYPE
              SYNTAX  DisplayString
              ACCESS  read-only
              STATUS  mandatory
              DESCRIPTION
                      "A unique value containing sensortype and serial number."
              ::= { s85 1 }

	    s85value OBJECT-TYPE
              SYNTAX  DisplayString
              ACCESS  read-only
              STATUS  mandatory
              DESCRIPTION
                      "The value of the sensor as String."
              ::= { s85 2 }

	    s85unit OBJECT-TYPE
              SYNTAX  DisplayString
              ACCESS  read-only
              STATUS  mandatory
              DESCRIPTION
                      "The unit of the sensor."
              ::= { s85 3 }

	    s85valueInt OBJECT-TYPE
              SYNTAX  INTEGER
              ACCESS  read-write
              STATUS  mandatory
              DESCRIPTION
                      "The value of the sensor times 1000 as integer"
              ::= { s85 4 }

	    s85name OBJECT-TYPE
              SYNTAX  DisplayString
              ACCESS  read-only
              STATUS  mandatory
              DESCRIPTION
                      "The name of the sensor as String. 
		       This name is set by the user in the SNMP Config Table."
              ::= { s85 5 }

	    s85alarmInt OBJECT-TYPE
              SYNTAX  INTEGER
              ACCESS  read-only
              STATUS  mandatory
              DESCRIPTION
                      "The Sensor Alarm Status range 1..5 as integer"
              ::= { s85 6 }

	    s85LoLimitAlarmInt OBJECT-TYPE
              SYNTAX  INTEGER
              ACCESS  read-only
              STATUS  mandatory
              DESCRIPTION
                      "The lower limit alarm value of the sensor times 1000 as integer"
              ::= { s85 7 }

	    s85LoLimitWarnInt OBJECT-TYPE
              SYNTAX  INTEGER
              ACCESS  read-only
              STATUS  mandatory
              DESCRIPTION
                      "The lower limit warning value of the sensor times 1000 as integer"
              ::= { s85 8 }

	    s85HiLimitWarnInt OBJECT-TYPE
              SYNTAX  INTEGER
              ACCESS  read-only
              STATUS  mandatory
              DESCRIPTION
                      "The upper limit warning value of the sensor times 1000 as integer"
              ::= { s85 9 }

	    s85HiLimitAlarmInt OBJECT-TYPE
              SYNTAX  INTEGER
              ACCESS  read-only
              STATUS  mandatory
              DESCRIPTION
                      "The upper limit alarm value of the sensor times 1000 as integer"
              ::= { s85 10 }

	    s85HysterInt OBJECT-TYPE
              SYNTAX  INTEGER
              ACCESS  read-only
              STATUS  mandatory
              DESCRIPTION
                      "The hysteresis value of the sensor times 1000 as integer"
              ::= { s85 11 }


	-- sensor86:
            s86id OBJECT-TYPE
              SYNTAX  DisplayString
              ACCESS  read-only
              STATUS  mandatory
              DESCRIPTION
                      "A unique value containing sensortype and serial number."
              ::= { s86 1 }

	    s86value OBJECT-TYPE
              SYNTAX  DisplayString
              ACCESS  read-only
              STATUS  mandatory
              DESCRIPTION
                      "The value of the sensor as String."
              ::= { s86 2 }

	    s86unit OBJECT-TYPE
              SYNTAX  DisplayString
              ACCESS  read-only
              STATUS  mandatory
              DESCRIPTION
                      "The unit of the sensor."
              ::= { s86 3 }

	    s86valueInt OBJECT-TYPE
              SYNTAX  INTEGER
              ACCESS  read-write
              STATUS  mandatory
              DESCRIPTION
                      "The value of the sensor times 1000 as integer"
              ::= { s86 4 }

	    s86name OBJECT-TYPE
              SYNTAX  DisplayString
              ACCESS  read-only
              STATUS  mandatory
              DESCRIPTION
                      "The name of the sensor as String. 
		       This name is set by the user in the SNMP Config Table."
              ::= { s86 5 }

	    s86alarmInt OBJECT-TYPE
              SYNTAX  INTEGER
              ACCESS  read-only
              STATUS  mandatory
              DESCRIPTION
                      "The Sensor Alarm Status range 1..5 as integer"
              ::= { s86 6 }

	    s86LoLimitAlarmInt OBJECT-TYPE
              SYNTAX  INTEGER
              ACCESS  read-only
              STATUS  mandatory
              DESCRIPTION
                      "The lower limit alarm value of the sensor times 1000 as integer"
              ::= { s86 7 }

	    s86LoLimitWarnInt OBJECT-TYPE
              SYNTAX  INTEGER
              ACCESS  read-only
              STATUS  mandatory
              DESCRIPTION
                      "The lower limit warning value of the sensor times 1000 as integer"
              ::= { s86 8 }

	    s86HiLimitWarnInt OBJECT-TYPE
              SYNTAX  INTEGER
              ACCESS  read-only
              STATUS  mandatory
              DESCRIPTION
                      "The upper limit warning value of the sensor times 1000 as integer"
              ::= { s86 9 }

	    s86HiLimitAlarmInt OBJECT-TYPE
              SYNTAX  INTEGER
              ACCESS  read-only
              STATUS  mandatory
              DESCRIPTION
                      "The upper limit alarm value of the sensor times 1000 as integer"
              ::= { s86 10 }

	    s86HysterInt OBJECT-TYPE
              SYNTAX  INTEGER
              ACCESS  read-only
              STATUS  mandatory
              DESCRIPTION
                      "The hysteresis value of the sensor times 1000 as integer"
              ::= { s86 11 }


	-- sensor87:
            s87id OBJECT-TYPE
              SYNTAX  DisplayString
              ACCESS  read-only
              STATUS  mandatory
              DESCRIPTION
                      "A unique value containing sensortype and serial number."
              ::= { s87 1 }

	    s87value OBJECT-TYPE
              SYNTAX  DisplayString
              ACCESS  read-only
              STATUS  mandatory
              DESCRIPTION
                      "The value of the sensor as String."
              ::= { s87 2 }

	    s87unit OBJECT-TYPE
              SYNTAX  DisplayString
              ACCESS  read-only
              STATUS  mandatory
              DESCRIPTION
                      "The unit of the sensor."
              ::= { s87 3 }

	    s87valueInt OBJECT-TYPE
              SYNTAX  INTEGER
              ACCESS  read-write
              STATUS  mandatory
              DESCRIPTION
                      "The value of the sensor times 1000 as integer"
              ::= { s87 4 }

	    s87name OBJECT-TYPE
              SYNTAX  DisplayString
              ACCESS  read-only
              STATUS  mandatory
              DESCRIPTION
                      "The name of the sensor as String. 
		       This name is set by the user in the SNMP Config Table."
              ::= { s87 5 }

	    s87alarmInt OBJECT-TYPE
              SYNTAX  INTEGER
              ACCESS  read-only
              STATUS  mandatory
              DESCRIPTION
                      "The Sensor Alarm Status range 1..5 as integer"
              ::= { s87 6 }

	    s87LoLimitAlarmInt OBJECT-TYPE
              SYNTAX  INTEGER
              ACCESS  read-only
              STATUS  mandatory
              DESCRIPTION
                      "The lower limit alarm value of the sensor times 1000 as integer"
              ::= { s87 7 }

	    s87LoLimitWarnInt OBJECT-TYPE
              SYNTAX  INTEGER
              ACCESS  read-only
              STATUS  mandatory
              DESCRIPTION
                      "The lower limit warning value of the sensor times 1000 as integer"
              ::= { s87 8 }

	    s87HiLimitWarnInt OBJECT-TYPE
              SYNTAX  INTEGER
              ACCESS  read-only
              STATUS  mandatory
              DESCRIPTION
                      "The upper limit warning value of the sensor times 1000 as integer"
              ::= { s87 9 }

	    s87HiLimitAlarmInt OBJECT-TYPE
              SYNTAX  INTEGER
              ACCESS  read-only
              STATUS  mandatory
              DESCRIPTION
                      "The upper limit alarm value of the sensor times 1000 as integer"
              ::= { s87 10 }

	    s87HysterInt OBJECT-TYPE
              SYNTAX  INTEGER
              ACCESS  read-only
              STATUS  mandatory
              DESCRIPTION
                      "The hysteresis value of the sensor times 1000 as integer"
              ::= { s87 11 }


	-- sensor88:
            s88id OBJECT-TYPE
              SYNTAX  DisplayString
              ACCESS  read-only
              STATUS  mandatory
              DESCRIPTION
                      "A unique value containing sensortype and serial number."
              ::= { s88 1 }

	    s88value OBJECT-TYPE
              SYNTAX  DisplayString
              ACCESS  read-only
              STATUS  mandatory
              DESCRIPTION
                      "The value of the sensor as String."
              ::= { s88 2 }

	    s88unit OBJECT-TYPE
              SYNTAX  DisplayString
              ACCESS  read-only
              STATUS  mandatory
              DESCRIPTION
                      "The unit of the sensor."
              ::= { s88 3 }

	    s88valueInt OBJECT-TYPE
              SYNTAX  INTEGER
              ACCESS  read-write
              STATUS  mandatory
              DESCRIPTION
                      "The value of the sensor times 1000 as integer"
              ::= { s88 4 }

	    s88name OBJECT-TYPE
              SYNTAX  DisplayString
              ACCESS  read-only
              STATUS  mandatory
              DESCRIPTION
                      "The name of the sensor as String. 
		       This name is set by the user in the SNMP Config Table."
              ::= { s88 5 }

	    s88alarmInt OBJECT-TYPE
              SYNTAX  INTEGER
              ACCESS  read-only
              STATUS  mandatory
              DESCRIPTION
                      "The Sensor Alarm Status range 1..5 as integer"
              ::= { s88 6 }

	    s88LoLimitAlarmInt OBJECT-TYPE
              SYNTAX  INTEGER
              ACCESS  read-only
              STATUS  mandatory
              DESCRIPTION
                      "The lower limit alarm value of the sensor times 1000 as integer"
              ::= { s88 7 }

	    s88LoLimitWarnInt OBJECT-TYPE
              SYNTAX  INTEGER
              ACCESS  read-only
              STATUS  mandatory
              DESCRIPTION
                      "The lower limit warning value of the sensor times 1000 as integer"
              ::= { s88 8 }

	    s88HiLimitWarnInt OBJECT-TYPE
              SYNTAX  INTEGER
              ACCESS  read-only
              STATUS  mandatory
              DESCRIPTION
                      "The upper limit warning value of the sensor times 1000 as integer"
              ::= { s88 9 }

	    s88HiLimitAlarmInt OBJECT-TYPE
              SYNTAX  INTEGER
              ACCESS  read-only
              STATUS  mandatory
              DESCRIPTION
                      "The upper limit alarm value of the sensor times 1000 as integer"
              ::= { s88 10 }

	    s88HysterInt OBJECT-TYPE
              SYNTAX  INTEGER
              ACCESS  read-only
              STATUS  mandatory
              DESCRIPTION
                      "The hysteresis value of the sensor times 1000 as integer"
              ::= { s88 11 }


	-- sensor89:
            s89id OBJECT-TYPE
              SYNTAX  DisplayString
              ACCESS  read-only
              STATUS  mandatory
              DESCRIPTION
                      "A unique value containing sensortype and serial number."
              ::= { s89 1 }

	    s89value OBJECT-TYPE
              SYNTAX  DisplayString
              ACCESS  read-only
              STATUS  mandatory
              DESCRIPTION
                      "The value of the sensor as String."
              ::= { s89 2 }

	    s89unit OBJECT-TYPE
              SYNTAX  DisplayString
              ACCESS  read-only
              STATUS  mandatory
              DESCRIPTION
                      "The unit of the sensor."
              ::= { s89 3 }

	    s89valueInt OBJECT-TYPE
              SYNTAX  INTEGER
              ACCESS  read-write
              STATUS  mandatory
              DESCRIPTION
                      "The value of the sensor times 1000 as integer"
              ::= { s89 4 }

	    s89name OBJECT-TYPE
              SYNTAX  DisplayString
              ACCESS  read-only
              STATUS  mandatory
              DESCRIPTION
                      "The name of the sensor as String. 
		       This name is set by the user in the SNMP Config Table."
              ::= { s89 5 }

	    s89alarmInt OBJECT-TYPE
              SYNTAX  INTEGER
              ACCESS  read-only
              STATUS  mandatory
              DESCRIPTION
                      "The Sensor Alarm Status range 1..5 as integer"
              ::= { s89 6 }

	    s89LoLimitAlarmInt OBJECT-TYPE
              SYNTAX  INTEGER
              ACCESS  read-only
              STATUS  mandatory
              DESCRIPTION
                      "The lower limit alarm value of the sensor times 1000 as integer"
              ::= { s89 7 }

	    s89LoLimitWarnInt OBJECT-TYPE
              SYNTAX  INTEGER
              ACCESS  read-only
              STATUS  mandatory
              DESCRIPTION
                      "The lower limit warning value of the sensor times 1000 as integer"
              ::= { s89 8 }

	    s89HiLimitWarnInt OBJECT-TYPE
              SYNTAX  INTEGER
              ACCESS  read-only
              STATUS  mandatory
              DESCRIPTION
                      "The upper limit warning value of the sensor times 1000 as integer"
              ::= { s89 9 }

	    s89HiLimitAlarmInt OBJECT-TYPE
              SYNTAX  INTEGER
              ACCESS  read-only
              STATUS  mandatory
              DESCRIPTION
                      "The upper limit alarm value of the sensor times 1000 as integer"
              ::= { s89 10 }

	    s89HysterInt OBJECT-TYPE
              SYNTAX  INTEGER
              ACCESS  read-only
              STATUS  mandatory
              DESCRIPTION
                      "The hysteresis value of the sensor times 1000 as integer"
              ::= { s89 11 }


	-- sensor90:
            s90id OBJECT-TYPE
              SYNTAX  DisplayString
              ACCESS  read-only
              STATUS  mandatory
              DESCRIPTION
                      "A unique value containing sensortype and serial number."
              ::= { s90 1 }

	    s90value OBJECT-TYPE
              SYNTAX  DisplayString
              ACCESS  read-only
              STATUS  mandatory
              DESCRIPTION
                      "The value of the sensor as String."
              ::= { s90 2 }

	    s90unit OBJECT-TYPE
              SYNTAX  DisplayString
              ACCESS  read-only
              STATUS  mandatory
              DESCRIPTION
                      "The unit of the sensor."
              ::= { s90 3 }

	    s90valueInt OBJECT-TYPE
              SYNTAX  INTEGER
              ACCESS  read-write
              STATUS  mandatory
              DESCRIPTION
                      "The value of the sensor times 1000 as integer"
              ::= { s90 4 }

	    s90name OBJECT-TYPE
              SYNTAX  DisplayString
              ACCESS  read-only
              STATUS  mandatory
              DESCRIPTION
                      "The name of the sensor as String. 
		       This name is set by the user in the SNMP Config Table."
              ::= { s90 5 }

	    s90alarmInt OBJECT-TYPE
              SYNTAX  INTEGER
              ACCESS  read-only
              STATUS  mandatory
              DESCRIPTION
                      "The Sensor Alarm Status range 1..5 as integer"
              ::= { s90 6 }

	    s90LoLimitAlarmInt OBJECT-TYPE
              SYNTAX  INTEGER
              ACCESS  read-only
              STATUS  mandatory
              DESCRIPTION
                      "The lower limit alarm value of the sensor times 1000 as integer"
              ::= { s90 7 }

	    s90LoLimitWarnInt OBJECT-TYPE
              SYNTAX  INTEGER
              ACCESS  read-only
              STATUS  mandatory
              DESCRIPTION
                      "The lower limit warning value of the sensor times 1000 as integer"
              ::= { s90 8 }

	    s90HiLimitWarnInt OBJECT-TYPE
              SYNTAX  INTEGER
              ACCESS  read-only
              STATUS  mandatory
              DESCRIPTION
                      "The upper limit warning value of the sensor times 1000 as integer"
              ::= { s90 9 }

	    s90HiLimitAlarmInt OBJECT-TYPE
              SYNTAX  INTEGER
              ACCESS  read-only
              STATUS  mandatory
              DESCRIPTION
                      "The upper limit alarm value of the sensor times 1000 as integer"
              ::= { s90 10 }

	    s90HysterInt OBJECT-TYPE
              SYNTAX  INTEGER
              ACCESS  read-only
              STATUS  mandatory
              DESCRIPTION
                      "The hysteresis value of the sensor times 1000 as integer"
              ::= { s90 11 }


  --  91 - 100
	-- sensor91:
            s91id OBJECT-TYPE
              SYNTAX  DisplayString
              ACCESS  read-only
              STATUS  mandatory
              DESCRIPTION
                      "A unique value containing sensortype and serial number."
              ::= { s91 1 }

	    s91value OBJECT-TYPE
              SYNTAX  DisplayString
              ACCESS  read-only
              STATUS  mandatory
              DESCRIPTION
                      "The value of the sensor as String."
              ::= { s91 2 }

	    s91unit OBJECT-TYPE
              SYNTAX  DisplayString
              ACCESS  read-only
              STATUS  mandatory
              DESCRIPTION
                      "The unit of the sensor."
              ::= { s91 3 }

	    s91valueInt OBJECT-TYPE
              SYNTAX  INTEGER
              ACCESS  read-write
              STATUS  mandatory
              DESCRIPTION
                      "The value of the sensor times 1000 as integer"
              ::= { s91 4 }

	    s91name OBJECT-TYPE
              SYNTAX  DisplayString
              ACCESS  read-only
              STATUS  mandatory
              DESCRIPTION
                      "The name of the sensor as String. 
		       This name is set by the user in the SNMP Config Table."
              ::= { s91 5 }

	    s91alarmInt OBJECT-TYPE
              SYNTAX  INTEGER
              ACCESS  read-only
              STATUS  mandatory
              DESCRIPTION
                      "The Sensor Alarm Status range 1..5 as integer"
              ::= { s91 6 }

	    s91LoLimitAlarmInt OBJECT-TYPE
              SYNTAX  INTEGER
              ACCESS  read-only
              STATUS  mandatory
              DESCRIPTION
                      "The lower limit alarm value of the sensor times 1000 as integer"
              ::= { s91 7 }

	    s91LoLimitWarnInt OBJECT-TYPE
              SYNTAX  INTEGER
              ACCESS  read-only
              STATUS  mandatory
              DESCRIPTION
                      "The lower limit warning value of the sensor times 1000 as integer"
              ::= { s91 8 }

	    s91HiLimitWarnInt OBJECT-TYPE
              SYNTAX  INTEGER
              ACCESS  read-only
              STATUS  mandatory
              DESCRIPTION
                      "The upper limit warning value of the sensor times 1000 as integer"
              ::= { s91 9 }

	    s91HiLimitAlarmInt OBJECT-TYPE
              SYNTAX  INTEGER
              ACCESS  read-only
              STATUS  mandatory
              DESCRIPTION
                      "The upper limit alarm value of the sensor times 1000 as integer"
              ::= { s91 10 }

	    s91HysterInt OBJECT-TYPE
              SYNTAX  INTEGER
              ACCESS  read-only
              STATUS  mandatory
              DESCRIPTION
                      "The hysteresis value of the sensor times 1000 as integer"
              ::= { s91 11 }


	-- sensor92:
            s92id OBJECT-TYPE
              SYNTAX  DisplayString
              ACCESS  read-only
              STATUS  mandatory
              DESCRIPTION
                      "A unique value containing sensortype and serial number."
              ::= { s92 1 }

	    s92value OBJECT-TYPE
              SYNTAX  DisplayString
              ACCESS  read-only
              STATUS  mandatory
              DESCRIPTION
                      "The value of the sensor as String."
              ::= { s92 2 }

	    s92unit OBJECT-TYPE
              SYNTAX  DisplayString
              ACCESS  read-only
              STATUS  mandatory
              DESCRIPTION
                      "The unit of the sensor."
              ::= { s92 3 }

	    s92valueInt OBJECT-TYPE
              SYNTAX  INTEGER
              ACCESS  read-write
              STATUS  mandatory
              DESCRIPTION
                      "The value of the sensor times 1000 as integer"
              ::= { s92 4 }

	    s92name OBJECT-TYPE
              SYNTAX  DisplayString
              ACCESS  read-only
              STATUS  mandatory
              DESCRIPTION
                      "The name of the sensor as String. 
		       This name is set by the user in the SNMP Config Table."
              ::= { s92 5 }

	    s92alarmInt OBJECT-TYPE
              SYNTAX  INTEGER
              ACCESS  read-only
              STATUS  mandatory
              DESCRIPTION
                      "The Sensor Alarm Status range 1..5 as integer"
              ::= { s92 6 }

	    s92LoLimitAlarmInt OBJECT-TYPE
              SYNTAX  INTEGER
              ACCESS  read-only
              STATUS  mandatory
              DESCRIPTION
                      "The lower limit alarm value of the sensor times 1000 as integer"
              ::= { s92 7 }

	    s92LoLimitWarnInt OBJECT-TYPE
              SYNTAX  INTEGER
              ACCESS  read-only
              STATUS  mandatory
              DESCRIPTION
                      "The lower limit warning value of the sensor times 1000 as integer"
              ::= { s92 8 }

	    s92HiLimitWarnInt OBJECT-TYPE
              SYNTAX  INTEGER
              ACCESS  read-only
              STATUS  mandatory
              DESCRIPTION
                      "The upper limit warning value of the sensor times 1000 as integer"
              ::= { s92 9 }

	    s92HiLimitAlarmInt OBJECT-TYPE
              SYNTAX  INTEGER
              ACCESS  read-only
              STATUS  mandatory
              DESCRIPTION
                      "The upper limit alarm value of the sensor times 1000 as integer"
              ::= { s92 10 }

	    s92HysterInt OBJECT-TYPE
              SYNTAX  INTEGER
              ACCESS  read-only
              STATUS  mandatory
              DESCRIPTION
                      "The hysteresis value of the sensor times 1000 as integer"
              ::= { s92 11 }


	-- sensor93:
            s93id OBJECT-TYPE
              SYNTAX  DisplayString
              ACCESS  read-only
              STATUS  mandatory
              DESCRIPTION
                      "A unique value containing sensortype and serial number."
              ::= { s93 1 }

	    s93value OBJECT-TYPE
              SYNTAX  DisplayString
              ACCESS  read-only
              STATUS  mandatory
              DESCRIPTION
                      "The value of the sensor as String."
              ::= { s93 2 }

	    s93unit OBJECT-TYPE
              SYNTAX  DisplayString
              ACCESS  read-only
              STATUS  mandatory
              DESCRIPTION
                      "The unit of the sensor."
              ::= { s93 3 }

	    s93valueInt OBJECT-TYPE
              SYNTAX  INTEGER
              ACCESS  read-write
              STATUS  mandatory
              DESCRIPTION
                      "The value of the sensor times 1000 as integer"
              ::= { s93 4 }

	    s93name OBJECT-TYPE
              SYNTAX  DisplayString
              ACCESS  read-only
              STATUS  mandatory
              DESCRIPTION
                      "The name of the sensor as String. 
		       This name is set by the user in the SNMP Config Table."
              ::= { s93 5 }

	    s93alarmInt OBJECT-TYPE
              SYNTAX  INTEGER
              ACCESS  read-only
              STATUS  mandatory
              DESCRIPTION
                      "The Sensor Alarm Status range 1..5 as integer"
              ::= { s93 6 }

	    s93LoLimitAlarmInt OBJECT-TYPE
              SYNTAX  INTEGER
              ACCESS  read-only
              STATUS  mandatory
              DESCRIPTION
                      "The lower limit alarm value of the sensor times 1000 as integer"
              ::= { s93 7 }

	    s93LoLimitWarnInt OBJECT-TYPE
              SYNTAX  INTEGER
              ACCESS  read-only
              STATUS  mandatory
              DESCRIPTION
                      "The lower limit warning value of the sensor times 1000 as integer"
              ::= { s93 8 }

	    s93HiLimitWarnInt OBJECT-TYPE
              SYNTAX  INTEGER
              ACCESS  read-only
              STATUS  mandatory
              DESCRIPTION
                      "The upper limit warning value of the sensor times 1000 as integer"
              ::= { s93 9 }

	    s93HiLimitAlarmInt OBJECT-TYPE
              SYNTAX  INTEGER
              ACCESS  read-only
              STATUS  mandatory
              DESCRIPTION
                      "The upper limit alarm value of the sensor times 1000 as integer"
              ::= { s93 10 }

	    s93HysterInt OBJECT-TYPE
              SYNTAX  INTEGER
              ACCESS  read-only
              STATUS  mandatory
              DESCRIPTION
                      "The hysteresis value of the sensor times 1000 as integer"
              ::= { s93 11 }


	-- sensor94:
            s94id OBJECT-TYPE
              SYNTAX  DisplayString
              ACCESS  read-only
              STATUS  mandatory
              DESCRIPTION
                      "A unique value containing sensortype and serial number."
              ::= { s94 1 }

	    s94value OBJECT-TYPE
              SYNTAX  DisplayString
              ACCESS  read-only
              STATUS  mandatory
              DESCRIPTION
                      "The value of the sensor as String."
              ::= { s94 2 }

	    s94unit OBJECT-TYPE
              SYNTAX  DisplayString
              ACCESS  read-only
              STATUS  mandatory
              DESCRIPTION
                      "The unit of the sensor."
              ::= { s94 3 }

	    s94valueInt OBJECT-TYPE
              SYNTAX  INTEGER
              ACCESS  read-write
              STATUS  mandatory
              DESCRIPTION
                      "The value of the sensor times 1000 as integer"
              ::= { s94 4 }

	    s94name OBJECT-TYPE
              SYNTAX  DisplayString
              ACCESS  read-only
              STATUS  mandatory
              DESCRIPTION
                      "The name of the sensor as String. 
		       This name is set by the user in the SNMP Config Table."
              ::= { s94 5 }

	    s94alarmInt OBJECT-TYPE
              SYNTAX  INTEGER
              ACCESS  read-only
              STATUS  mandatory
              DESCRIPTION
                      "The Sensor Alarm Status range 1..5 as integer"
              ::= { s94 6 }

	    s94LoLimitAlarmInt OBJECT-TYPE
              SYNTAX  INTEGER
              ACCESS  read-only
              STATUS  mandatory
              DESCRIPTION
                      "The lower limit alarm value of the sensor times 1000 as integer"
              ::= { s94 7 }

	    s94LoLimitWarnInt OBJECT-TYPE
              SYNTAX  INTEGER
              ACCESS  read-only
              STATUS  mandatory
              DESCRIPTION
                      "The lower limit warning value of the sensor times 1000 as integer"
              ::= { s94 8 }

	    s94HiLimitWarnInt OBJECT-TYPE
              SYNTAX  INTEGER
              ACCESS  read-only
              STATUS  mandatory
              DESCRIPTION
                      "The upper limit warning value of the sensor times 1000 as integer"
              ::= { s94 9 }

	    s94HiLimitAlarmInt OBJECT-TYPE
              SYNTAX  INTEGER
              ACCESS  read-only
              STATUS  mandatory
              DESCRIPTION
                      "The upper limit alarm value of the sensor times 1000 as integer"
              ::= { s94 10 }

	    s94HysterInt OBJECT-TYPE
              SYNTAX  INTEGER
              ACCESS  read-only
              STATUS  mandatory
              DESCRIPTION
                      "The hysteresis value of the sensor times 1000 as integer"
              ::= { s94 11 }


	-- sensor95:
            s95id OBJECT-TYPE
              SYNTAX  DisplayString
              ACCESS  read-only
              STATUS  mandatory
              DESCRIPTION
                      "A unique value containing sensortype and serial number."
              ::= { s95 1 }

	    s95value OBJECT-TYPE
              SYNTAX  DisplayString
              ACCESS  read-only
              STATUS  mandatory
              DESCRIPTION
                      "The value of the sensor as String."
              ::= { s95 2 }

	    s95unit OBJECT-TYPE
              SYNTAX  DisplayString
              ACCESS  read-only
              STATUS  mandatory
              DESCRIPTION
                      "The unit of the sensor."
              ::= { s95 3 }

	    s95valueInt OBJECT-TYPE
              SYNTAX  INTEGER
              ACCESS  read-write
              STATUS  mandatory
              DESCRIPTION
                      "The value of the sensor times 1000 as integer"
              ::= { s95 4 }

	    s95name OBJECT-TYPE
              SYNTAX  DisplayString
              ACCESS  read-only
              STATUS  mandatory
              DESCRIPTION
                      "The name of the sensor as String. 
		       This name is set by the user in the SNMP Config Table."
              ::= { s95 5 }

	    s95alarmInt OBJECT-TYPE
              SYNTAX  INTEGER
              ACCESS  read-only
              STATUS  mandatory
              DESCRIPTION
                      "The Sensor Alarm Status range 1..5 as integer"
              ::= { s95 6 }

	    s95LoLimitAlarmInt OBJECT-TYPE
              SYNTAX  INTEGER
              ACCESS  read-only
              STATUS  mandatory
              DESCRIPTION
                      "The lower limit alarm value of the sensor times 1000 as integer"
              ::= { s95 7 }

	    s95LoLimitWarnInt OBJECT-TYPE
              SYNTAX  INTEGER
              ACCESS  read-only
              STATUS  mandatory
              DESCRIPTION
                      "The lower limit warning value of the sensor times 1000 as integer"
              ::= { s95 8 }

	    s95HiLimitWarnInt OBJECT-TYPE
              SYNTAX  INTEGER
              ACCESS  read-only
              STATUS  mandatory
              DESCRIPTION
                      "The upper limit warning value of the sensor times 1000 as integer"
              ::= { s95 9 }

	    s95HiLimitAlarmInt OBJECT-TYPE
              SYNTAX  INTEGER
              ACCESS  read-only
              STATUS  mandatory
              DESCRIPTION
                      "The upper limit alarm value of the sensor times 1000 as integer"
              ::= { s95 10 }

	    s95HysterInt OBJECT-TYPE
              SYNTAX  INTEGER
              ACCESS  read-only
              STATUS  mandatory
              DESCRIPTION
                      "The hysteresis value of the sensor times 1000 as integer"
              ::= { s95 11 }


	-- sensor96:
            s96id OBJECT-TYPE
              SYNTAX  DisplayString
              ACCESS  read-only
              STATUS  mandatory
              DESCRIPTION
                      "A unique value containing sensortype and serial number."
              ::= { s96 1 }

	    s96value OBJECT-TYPE
              SYNTAX  DisplayString
              ACCESS  read-only
              STATUS  mandatory
              DESCRIPTION
                      "The value of the sensor as String."
              ::= { s96 2 }

	    s96unit OBJECT-TYPE
              SYNTAX  DisplayString
              ACCESS  read-only
              STATUS  mandatory
              DESCRIPTION
                      "The unit of the sensor."
              ::= { s96 3 }

	    s96valueInt OBJECT-TYPE
              SYNTAX  INTEGER
              ACCESS  read-write
              STATUS  mandatory
              DESCRIPTION
                      "The value of the sensor times 1000 as integer"
              ::= { s96 4 }

	    s96name OBJECT-TYPE
              SYNTAX  DisplayString
              ACCESS  read-only
              STATUS  mandatory
              DESCRIPTION
                      "The name of the sensor as String. 
		       This name is set by the user in the SNMP Config Table."
              ::= { s96 5 }

	    s96alarmInt OBJECT-TYPE
              SYNTAX  INTEGER
              ACCESS  read-only
              STATUS  mandatory
              DESCRIPTION
                      "The Sensor Alarm Status range 1..5 as integer"
              ::= { s96 6 }

	    s96LoLimitAlarmInt OBJECT-TYPE
              SYNTAX  INTEGER
              ACCESS  read-only
              STATUS  mandatory
              DESCRIPTION
                      "The lower limit alarm value of the sensor times 1000 as integer"
              ::= { s96 7 }

	    s96LoLimitWarnInt OBJECT-TYPE
              SYNTAX  INTEGER
              ACCESS  read-only
              STATUS  mandatory
              DESCRIPTION
                      "The lower limit warning value of the sensor times 1000 as integer"
              ::= { s96 8 }

	    s96HiLimitWarnInt OBJECT-TYPE
              SYNTAX  INTEGER
              ACCESS  read-only
              STATUS  mandatory
              DESCRIPTION
                      "The upper limit warning value of the sensor times 1000 as integer"
              ::= { s96 9 }

	    s96HiLimitAlarmInt OBJECT-TYPE
              SYNTAX  INTEGER
              ACCESS  read-only
              STATUS  mandatory
              DESCRIPTION
                      "The upper limit alarm value of the sensor times 1000 as integer"
              ::= { s96 10 }

	    s96HysterInt OBJECT-TYPE
              SYNTAX  INTEGER
              ACCESS  read-only
              STATUS  mandatory
              DESCRIPTION
                      "The hysteresis value of the sensor times 1000 as integer"
              ::= { s96 11 }


	-- sensor97:
            s97id OBJECT-TYPE
              SYNTAX  DisplayString
              ACCESS  read-only
              STATUS  mandatory
              DESCRIPTION
                      "A unique value containing sensortype and serial number."
              ::= { s97 1 }

	    s97value OBJECT-TYPE
              SYNTAX  DisplayString
              ACCESS  read-only
              STATUS  mandatory
              DESCRIPTION
                      "The value of the sensor as String."
              ::= { s97 2 }

	    s97unit OBJECT-TYPE
              SYNTAX  DisplayString
              ACCESS  read-only
              STATUS  mandatory
              DESCRIPTION
                      "The unit of the sensor."
              ::= { s97 3 }

	    s97valueInt OBJECT-TYPE
              SYNTAX  INTEGER
              ACCESS  read-write
              STATUS  mandatory
              DESCRIPTION
                      "The value of the sensor times 1000 as integer"
              ::= { s97 4 }

	    s97name OBJECT-TYPE
              SYNTAX  DisplayString
              ACCESS  read-only
              STATUS  mandatory
              DESCRIPTION
                      "The name of the sensor as String. 
		       This name is set by the user in the SNMP Config Table."
              ::= { s97 5 }

	    s97alarmInt OBJECT-TYPE
              SYNTAX  INTEGER
              ACCESS  read-only
              STATUS  mandatory
              DESCRIPTION
                      "The Sensor Alarm Status range 1..5 as integer"
              ::= { s97 6 }

	    s97LoLimitAlarmInt OBJECT-TYPE
              SYNTAX  INTEGER
              ACCESS  read-only
              STATUS  mandatory
              DESCRIPTION
                      "The lower limit alarm value of the sensor times 1000 as integer"
              ::= { s97 7 }

	    s97LoLimitWarnInt OBJECT-TYPE
              SYNTAX  INTEGER
              ACCESS  read-only
              STATUS  mandatory
              DESCRIPTION
                      "The lower limit warning value of the sensor times 1000 as integer"
              ::= { s97 8 }

	    s97HiLimitWarnInt OBJECT-TYPE
              SYNTAX  INTEGER
              ACCESS  read-only
              STATUS  mandatory
              DESCRIPTION
                      "The upper limit warning value of the sensor times 1000 as integer"
              ::= { s97 9 }

	    s97HiLimitAlarmInt OBJECT-TYPE
              SYNTAX  INTEGER
              ACCESS  read-only
              STATUS  mandatory
              DESCRIPTION
                      "The upper limit alarm value of the sensor times 1000 as integer"
              ::= { s97 10 }

	    s97HysterInt OBJECT-TYPE
              SYNTAX  INTEGER
              ACCESS  read-only
              STATUS  mandatory
              DESCRIPTION
                      "The hysteresis value of the sensor times 1000 as integer"
              ::= { s97 11 }


	-- sensor98:
            s98id OBJECT-TYPE
              SYNTAX  DisplayString
              ACCESS  read-only
              STATUS  mandatory
              DESCRIPTION
                      "A unique value containing sensortype and serial number."
              ::= { s98 1 }

	    s98value OBJECT-TYPE
              SYNTAX  DisplayString
              ACCESS  read-only
              STATUS  mandatory
              DESCRIPTION
                      "The value of the sensor as String."
              ::= { s98 2 }

	    s98unit OBJECT-TYPE
              SYNTAX  DisplayString
              ACCESS  read-only
              STATUS  mandatory
              DESCRIPTION
                      "The unit of the sensor."
              ::= { s98 3 }

	    s98valueInt OBJECT-TYPE
              SYNTAX  INTEGER
              ACCESS  read-write
              STATUS  mandatory
              DESCRIPTION
                      "The value of the sensor times 1000 as integer"
              ::= { s98 4 }

	    s98name OBJECT-TYPE
              SYNTAX  DisplayString
              ACCESS  read-only
              STATUS  mandatory
              DESCRIPTION
                      "The name of the sensor as String. 
		       This name is set by the user in the SNMP Config Table."
              ::= { s98 5 }

	    s98alarmInt OBJECT-TYPE
              SYNTAX  INTEGER
              ACCESS  read-only
              STATUS  mandatory
              DESCRIPTION
                      "The Sensor Alarm Status range 1..5 as integer"
              ::= { s98 6 }

	    s98LoLimitAlarmInt OBJECT-TYPE
              SYNTAX  INTEGER
              ACCESS  read-only
              STATUS  mandatory
              DESCRIPTION
                      "The lower limit alarm value of the sensor times 1000 as integer"
              ::= { s98 7 }

	    s98LoLimitWarnInt OBJECT-TYPE
              SYNTAX  INTEGER
              ACCESS  read-only
              STATUS  mandatory
              DESCRIPTION
                      "The lower limit warning value of the sensor times 1000 as integer"
              ::= { s98 8 }

	    s98HiLimitWarnInt OBJECT-TYPE
              SYNTAX  INTEGER
              ACCESS  read-only
              STATUS  mandatory
              DESCRIPTION
                      "The upper limit warning value of the sensor times 1000 as integer"
              ::= { s98 9 }

	    s98HiLimitAlarmInt OBJECT-TYPE
              SYNTAX  INTEGER
              ACCESS  read-only
              STATUS  mandatory
              DESCRIPTION
                      "The upper limit alarm value of the sensor times 1000 as integer"
              ::= { s98 10 }

	    s98HysterInt OBJECT-TYPE
              SYNTAX  INTEGER
              ACCESS  read-only
              STATUS  mandatory
              DESCRIPTION
                      "The hysteresis value of the sensor times 1000 as integer"
              ::= { s98 11 }


	-- sensor99:
            s99id OBJECT-TYPE
              SYNTAX  DisplayString
              ACCESS  read-only
              STATUS  mandatory
              DESCRIPTION
                      "A unique value containing sensortype and serial number."
              ::= { s99 1 }

	    s99value OBJECT-TYPE
              SYNTAX  DisplayString
              ACCESS  read-only
              STATUS  mandatory
              DESCRIPTION
                      "The value of the sensor as String."
              ::= { s99 2 }

	    s99unit OBJECT-TYPE
              SYNTAX  DisplayString
              ACCESS  read-only
              STATUS  mandatory
              DESCRIPTION
                      "The unit of the sensor."
              ::= { s99 3 }

	    s99valueInt OBJECT-TYPE
              SYNTAX  INTEGER
              ACCESS  read-write
              STATUS  mandatory
              DESCRIPTION
                      "The value of the sensor times 1000 as integer"
              ::= { s99 4 }

	    s99name OBJECT-TYPE
              SYNTAX  DisplayString
              ACCESS  read-only
              STATUS  mandatory
              DESCRIPTION
                      "The name of the sensor as String. 
		       This name is set by the user in the SNMP Config Table."
              ::= { s99 5 }

	    s99alarmInt OBJECT-TYPE
              SYNTAX  INTEGER
              ACCESS  read-only
              STATUS  mandatory
              DESCRIPTION
                      "The Sensor Alarm Status range 1..5 as integer"
              ::= { s99 6 }

	    s99LoLimitAlarmInt OBJECT-TYPE
              SYNTAX  INTEGER
              ACCESS  read-only
              STATUS  mandatory
              DESCRIPTION
                      "The lower limit alarm value of the sensor times 1000 as integer"
              ::= { s99 7 }

	    s99LoLimitWarnInt OBJECT-TYPE
              SYNTAX  INTEGER
              ACCESS  read-only
              STATUS  mandatory
              DESCRIPTION
                      "The lower limit warning value of the sensor times 1000 as integer"
              ::= { s99 8 }

	    s99HiLimitWarnInt OBJECT-TYPE
              SYNTAX  INTEGER
              ACCESS  read-only
              STATUS  mandatory
              DESCRIPTION
                      "The upper limit warning value of the sensor times 1000 as integer"
              ::= { s99 9 }

	    s99HiLimitAlarmInt OBJECT-TYPE
              SYNTAX  INTEGER
              ACCESS  read-only
              STATUS  mandatory
              DESCRIPTION
                      "The upper limit alarm value of the sensor times 1000 as integer"
              ::= { s99 10 }

	    s99HysterInt OBJECT-TYPE
              SYNTAX  INTEGER
              ACCESS  read-only
              STATUS  mandatory
              DESCRIPTION
                      "The hysteresis value of the sensor times 1000 as integer"
              ::= { s99 11 }


	-- sensor100:
            s100id OBJECT-TYPE
              SYNTAX  DisplayString
              ACCESS  read-only
              STATUS  mandatory
              DESCRIPTION
                      "A unique value containing sensortype and serial number."
              ::= { s100 1 }

	    s100value OBJECT-TYPE
              SYNTAX  DisplayString
              ACCESS  read-only
              STATUS  mandatory
              DESCRIPTION
                      "The value of the sensor as String."
              ::= { s100 2 }

	    s100unit OBJECT-TYPE
              SYNTAX  DisplayString
              ACCESS  read-only
              STATUS  mandatory
              DESCRIPTION
                      "The unit of the sensor."
              ::= { s100 3 }

	    s100valueInt OBJECT-TYPE
              SYNTAX  INTEGER
              ACCESS  read-write
              STATUS  mandatory
              DESCRIPTION
                      "The value of the sensor times 1000 as integer"
              ::= { s100 4 }

	    s100name OBJECT-TYPE
              SYNTAX  DisplayString
              ACCESS  read-only
              STATUS  mandatory
              DESCRIPTION
                      "The name of the sensor as String. 
		       This name is set by the user in the SNMP Config Table."
              ::= { s100 5 }

	    s100alarmInt OBJECT-TYPE
              SYNTAX  INTEGER
              ACCESS  read-only
              STATUS  mandatory
              DESCRIPTION
                      "The Sensor Alarm Status range 1..5 as integer"
              ::= { s100 6 }

	    s100LoLimitAlarmInt OBJECT-TYPE
              SYNTAX  INTEGER
              ACCESS  read-only
              STATUS  mandatory
              DESCRIPTION
                      "The lower limit alarm value of the sensor times 1000 as integer"
              ::= { s100 7 }

	    s100LoLimitWarnInt OBJECT-TYPE
              SYNTAX  INTEGER
              ACCESS  read-only
              STATUS  mandatory
              DESCRIPTION
                      "The lower limit warning value of the sensor times 1000 as integer"
              ::= { s100 8 }

	    s100HiLimitWarnInt OBJECT-TYPE
              SYNTAX  INTEGER
              ACCESS  read-only
              STATUS  mandatory
              DESCRIPTION
                      "The upper limit warning value of the sensor times 1000 as integer"
              ::= { s100 9 }

	    s100HiLimitAlarmInt OBJECT-TYPE
              SYNTAX  INTEGER
              ACCESS  read-only
              STATUS  mandatory
              DESCRIPTION
                      "The upper limit alarm value of the sensor times 1000 as integer"
              ::= { s100 10 }

	    s100HysterInt OBJECT-TYPE
              SYNTAX  INTEGER
              ACCESS  read-only
              STATUS  mandatory
              DESCRIPTION
                      "The hysteresis value of the sensor times 1000 as integer"
              ::= { s100 11 }







-- -------------------------------------------------------------------
-- Number of Alarms in sguard

          numAlarms OBJECT-TYPE
              SYNTAX  INTEGER
              ACCESS  read-only
              STATUS  mandatory

              DESCRIPTION
                      "Number of Alarms of connected sensors"
              ::= { sguard 4 }











	--   ************   TRAP Definitions for all   *************

	alarmSource OBJECT-TYPE
		SYNTAX DisplayString
		ACCESS read-only
		STATUS mandatory
		::= {sguard 19998}

	alarmString OBJECT-TYPE
		SYNTAX DisplayString
		ACCESS read-only
		STATUS mandatory
		::= {sguard 19999}

	sguardTrap01 TRAP-TYPE
		ENTERPRISE sguard
		VARIABLES   { alarmString, alarmSource }
		DESCRIPTION
			"This trap can be freely configured."
		::= 1

	sguardTrap02 TRAP-TYPE
		ENTERPRISE sguard
		VARIABLES   { alarmString, alarmSource }
		DESCRIPTION
			"This trap can be freely configured."
		::= 2

	sguardTrap03 TRAP-TYPE
		ENTERPRISE sguard
		VARIABLES   { alarmString, alarmSource }
		DESCRIPTION
			"This trap can be freely configured."
		::= 3

	sguardTrap04 TRAP-TYPE
		ENTERPRISE sguard
		VARIABLES   { alarmString, alarmSource }
		DESCRIPTION
			"This trap can be freely configured."
		::= 4

	sguardTrap05 TRAP-TYPE
		ENTERPRISE sguard
		VARIABLES   { alarmString, alarmSource }
		DESCRIPTION
			"This trap can be freely configured."
		::= 5

	sguardTrap06 TRAP-TYPE
		ENTERPRISE sguard
		VARIABLES   { alarmString, alarmSource }
		DESCRIPTION
			"This trap can be freely configured."
		::= 6

	sguardTrap07 TRAP-TYPE
		ENTERPRISE sguard
		VARIABLES   { alarmString, alarmSource }
		DESCRIPTION
			"This trap can be freely configured."
		::= 7

	sguardTrap08 TRAP-TYPE
		ENTERPRISE sguard
		VARIABLES   { alarmString, alarmSource }
		DESCRIPTION
			"This trap can be freely configured."
		::= 8

	sguardTrap09 TRAP-TYPE
		ENTERPRISE sguard
		VARIABLES   { alarmString, alarmSource }
		DESCRIPTION
			"This trap can be freely configured."
		::= 9

	sguardTrap10 TRAP-TYPE
		ENTERPRISE sguard
		VARIABLES   { alarmString, alarmSource }
		DESCRIPTION
			"This trap can be freely configured."
		::= 10
	      
	      END
