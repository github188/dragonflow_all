-- =============================================================================
-- Copyright (C) 2006 by HUAWEI-3COM TECHNOLOGIES.  All rights reserved.
--
-- Description:
--   The file defines a MIB to provide root node and TC for 802.11 MIB series.
-- Reference:
-- =============================================================================
H3C-DOT11-REF-MIB DEFINITIONS ::= BEGIN

IMPORTS
        TEXTUAL-CONVENTION
    FROM SNMPv2-TC
        MODULE-IDENTITY,
        Integer32
    FROM SNMPv2-SMI
        h3cCommon
    FROM HUAWEI-3COM-OID-MIB;

h3cDot11 MODULE-IDENTITY
    LAST-UPDATED "200706212000Z"        -- Jun 21, 2007 at 20:00 GMT
    ORGANIZATION
        "HUAWEI-3COM Technologies Co., Ltd."
    CONTACT-INFO
        "Platform Team HUAWEI-3COM Technologies Co., Ltd.
         Hai-Dian District Beijing P.R. China
         Http://www.huawei-3com.com
         Zip:100085"
    DESCRIPTION
        "This MIB defines the root node and TC for 802.11 features.
        By this way, the MIB series for 802.11 will be easily maintained.

        GLOSSARY

        IEEE 802.11
        Standard to encourage interoperability among
        wireless networking equipment.

        IEEE 802.11a
        This is a high speed physical layer extension to
        the 802.11 standard on the 5 GHz band.

        IEEE 802.11b
        High-rate wireless LAN standard for wireless
        data transfer at up to 11 Mbps.

        IEEE 802.11g
        Higher Speed Physical Layer (PHY) Extension to
        IEEE 802.11b, will boost wireless LAN speed to 54
        Mbps by using OFDM (orthogonal frequency division
        multiplexing). The IEEE 802.11g specification is
        backward compatible with the widely deployed IEEE
        802.11b standard.
        When configure radio with as bg mode, it means that
        radio will be compatible to 802.11b and 802.11g.
        When configure radio with as g mode, it means that
        radio will be only compatible to 802.11g.

        IEEE 802.11i
        As 802.11 has lot of deficiency in wireless security
        domain, especially for enterprise custom, IEEE defined
        a new standard 802.11i to extend security feature of
        802.11 standard.

        AKM
        The authentication and key management method defined by
        802.11i, and which includes 802.1x and pre-shared key."

    REVISION "200706212000Z"        -- Jun 21, 2007 at 20:00 GMT
    DESCRIPTION
        "Modified for CMCC(China Mobile Communication Corporation)
        requirements."
    REVISION "200704272000Z"        -- Apr 27, 2007 at 20:00 GMT
    DESCRIPTION
        "Modified to add new TC."
    REVISION "200605101900Z"        -- May 10, 2006 at 19:00 GMT
    DESCRIPTION
        "The initial revision of this MIB module."
    ::= { h3cCommon 75 }

-- *****************************************************************************
-- *  Textual conventions from 802 definitions
-- *****************************************************************************
--  Common TEXTUAL-CONVENTION
H3cDot11ObjectIDType ::=   TEXTUAL-CONVENTION
    STATUS      current
    DESCRIPTION
        "Represents AP identifier value type."
    SYNTAX      OCTET STRING(SIZE(0..127))

H3cDot11RadioScopeType ::=   TEXTUAL-CONVENTION
    STATUS      current
    DESCRIPTION
        "Represents radio value scope."
    SYNTAX      Integer32

H3cDot11RadioType ::=   TEXTUAL-CONVENTION
    STATUS      current
    DESCRIPTION
        "Represents AP 802.11 radio type of 802.11a/b/g/n as per
        the standard.
        The following values are supported:
        dot11a(1)  - 802.11a
        dot11b(2)  - 802.11b
        dot11g(4)  - 802.11g
        dot11n(8)  - 802.11n"
    SYNTAX      INTEGER
        {
            dot11a(1),
            dot11b(2),
            dot11g(4),
            dot11n(8)
        }

H3cDot11MACModeType ::=   TEXTUAL-CONVENTION
    STATUS      current
    DESCRIPTION
        "CAPWAP defines three kinds MAC mode for fit AP.
        The management packet will be exchanged between AP and AC by
        CAPWAP control tunnel.
        For data packet, the following MAC mode are supported:
        split(1)        - AP will tunnel 802.11 data message
        - to AC by CAPWAP,
        localtunnel(2)  - AP will convert data to 802.3, then tunnel
        - it to AC by CAPWAP,
        localbridge(3)  - AP will directly handle data packet without
        - sending to AC to process,
        fatAP           - For fat AP, it will handle all 802.11 frames
        - by itself."
    SYNTAX      INTEGER
        {
            split(1),
            localtunnel(2),
            localbridge(3),
            fatAP(4)
        }

H3cDot11ChannelScopeType ::=   TEXTUAL-CONVENTION
    STATUS      current
    DESCRIPTION
        "Represents the channel scope which consists of 802.11a/b/g."
    SYNTAX      Integer32

H3cDot11NotifyReasonType ::=   TEXTUAL-CONVENTION
    STATUS      current
    DESCRIPTION
        "The explanation string is for the event notification of dot11."
    SYNTAX      OCTET STRING(SIZE(0..255))

H3cDot11SSIDStringType ::=   TEXTUAL-CONVENTION
    STATUS      current
    DESCRIPTION
        "SSID is a string to identify ESS for wireless network."
    SYNTAX      OCTET STRING

H3cDot11ServicePolicyIDType ::=   TEXTUAL-CONVENTION
    STATUS      current
    DESCRIPTION
        "Represents the type of service policy ID."
    SYNTAX      Integer32

H3cDot11SSIDEncryptModeType ::=   TEXTUAL-CONVENTION
    STATUS      current
    DESCRIPTION
        "Represents encryption mode for the specific ESS:
        The following values are supported:
        cleartxt(1)  - clear txt,
        cipher(2)    - WPA and 802.11i"
    SYNTAX      INTEGER
        {
            cleartxt(1),
            cipher(2)
        }

H3cDot11PreambleType ::=   TEXTUAL-CONVENTION
    STATUS      current
    DESCRIPTION
        "Represents the current radio preamble type.
        The following values are supported:
        long(1)  - long preambles,
        short(2) - short preambles."
    SYNTAX      INTEGER
        {
            long(1),
            short(2)
        }

H3cDot11TxPwrLevelScopeType ::=   TEXTUAL-CONVENTION
    STATUS      current
    DESCRIPTION
        "Represents the Tx power level scope for 802.11."
    SYNTAX      Integer32

H3cDot11RFModeType ::=   TEXTUAL-CONVENTION
    STATUS      current
    DESCRIPTION
        "Represents RF management mode.
        The following values are supported:
        manual(1)  - Configure RF parameter by manual,
        auto(2)    - Automaticall configure."
    SYNTAX      INTEGER
        {
            manual(1),
            auto(2)
        }

--  CAPWAP TEXTUAL-CONVENTION
H3cDot11TunnelSecSchemType ::=   TEXTUAL-CONVENTION
    STATUS      current
    DESCRIPTION
        "Represents which security scheme option is available for
        CAPWAP tunnel.
        The following values are supported:
        cleartxt(1)  - No encryption protection,
        dtls(2)      - Encrypted by DTLS,
        ipsec(3)     - Encrypted by IPSEC."
    SYNTAX      INTEGER
        {
            cleartxt(1),
            dtls(2),
            ipsec(3)
        }

--  802.11i TEXTUAL-CONVENTION
H3cDot11SecIEStatusType ::=   TEXTUAL-CONVENTION
    STATUS      current
    DESCRIPTION
        "To enable the WPA Information element in the beacon and probe
        response frames sent by AP.
        The following values are supported:
        none(1) - both wpa and rsn are disabled,
        rsn(2)  - only enable rsn,
        wpa(3)  - only enable wpa,
        all(4)  - both wpa and rsn are enabled."
    SYNTAX      INTEGER
        {
            none(1),
            rsn(2),
            wpa(3),
            all(4)
        }

H3cDot11CipherType ::=   TEXTUAL-CONVENTION
    STATUS      current
    DESCRIPTION
        "Represents the frame encryption cipher types for
        frames on IEEE 802.11 radio interfaces.
        The MIB defines TC by referring to the 802.11i protocol.
        The following values are supported:
        none(1)     - clear text or no cipher method is configure,
        wep40(2)    - 40-bit WEP key,
        tkip(4)     - WPA Temporal Key encryption,
        aesccmp(16) - WPA AES CCMP encryption,
        wep104(32)  - 104-bit WEP key."
    SYNTAX      INTEGER
        {
            none(1),
            wep40(2),
            tkip(4),
            aesccmp(16),
            wep104(32)
        }

H3cDot11AuthenType ::=   TEXTUAL-CONVENTION
    STATUS      current
    DESCRIPTION
        "Represents the Authentication mode defined by 802.11.
        The following values are supported:
        none(1)         - No authentication mode configured,
        opensystem(2)   - In fact,no real authentication happened,
        sharedkey(3)    - System will use challenge message to
        - authenticate the access user,
        all(4)          - both open system and shared key."
    SYNTAX      INTEGER
        {
            none(1),
            opensystem(2),
            sharedkey(3),
            all(4)
        }

H3cDot11AKMType ::=   TEXTUAL-CONVENTION
    STATUS      current
    DESCRIPTION
        "Represents the key management mode defined by 802.11i.
        The following values are supported:
        none(1)         - No key management mode configured,
        psk(2)          - pre-shared key authentication,
        dot1x(3)        - 802.1x authentication."
    SYNTAX      INTEGER
        {
            none(1),
            psk(2),
            dot1x(3)
        }

H3cDot11AssocFailType ::=   TEXTUAL-CONVENTION
    STATUS      current
    DESCRIPTION
        "Enumeration of the reasons for station association failure.
        including:
        unknownfailure(1)          - unknown failure,
        toomanyassoc(2)            - too many association,
        invalidie(3)               - information element is invalid,
        unsupportedrate(4)         - rate is not supported,
        unsupportedpwrcap(5)       - power capability is not supported
        unsupportedcap(6)          - capability is not supported"
    SYNTAX      INTEGER
        {
            unknownfailure(1),
            toomanyassoc(2),
            invalidie(3),
            unsupportedrate(4),
            unsupportedpwrcap(5),
            unsupportedcap(6)
        }

H3cDot11AuthorFailType ::=   TEXTUAL-CONVENTION
    STATUS      current
    DESCRIPTION
        "Enumeration of the reasons for station authorization failure.
        including:
        unknownfailure(1)           - unknown failure,
        invalidie(2)                - information element is invalid,
        rsnieversionunsupported(3)  - rsn information element version
        is not supported,
        wpaieversionunsupported(4)  - wpa information element version
        is not supported,
        groupcipherinvalid(5)       - group cipher is invalid,
        pairwisecipherinvalid(6)    - pairwise cipher is invalid,
        akminvalid(7)               - akm is invalid"
    SYNTAX      INTEGER
        {
            unknownfailure(1),
            invalidie(2),
            rsnieversionunsupported(3),
            wpaieversionunsupported(4),
            groupcipherinvalid(5),
            pairwisecipherinvalid(6),
            akminvalid(7)
        }

--  802.11e TEXTUAL-CONVENTION
H3cDot11QosAcType ::=   TEXTUAL-CONVENTION
    STATUS      current
    DESCRIPTION
        "802.11e defines four types of access category, including:
        ac-bk(1)      - for background access category,
        ac-be(2)      - for besteffort access category,
        ac-vi(3)      - for voice access category,
        ac-vo(4)      - for video access category
        "
    SYNTAX      INTEGER
        {
            ac-bk(1),
            ac-be(2),
            ac-vi(3),
            ac-vo(4)
        }

-- *****************************************************************************
-- *  Major sections
-- *****************************************************************************
END
