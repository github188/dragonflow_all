-- ==========================================================================
-- Copyright (C) 2004 by H3C Technologies. All rights reserved.
--
-- Description: The purpose of this MIB file is to provide the the definition 
--              of the general digital voice interface configuration.
-- Reference:
-- ==========================================================================
HH3C-VODIGITALIF-MIB DEFINITIONS ::= BEGIN
        IMPORTS
            OBJECT-TYPE, MODULE-IDENTITY, Integer32
                FROM SNMPv2-SMI
        hh3cVoice
                FROM HH3C-OID-MIB;
    
        
        hh3cVoiceDigitalInterface  MODULE-IDENTITY 
            LAST-UPDATED "200503150000Z"
            ORGANIZATION
                "Hangzhou H3C Tech. Co., Ltd."
            CONTACT-INFO
                "Platform Team Hangzhou H3C Tech. Co., Ltd.
                Hai-Dian District Beijing P.R. China
                http://www.h3c.com
                Zip:100085
                "
            DESCRIPTION 
                "The MIB file is to provide the definition of the
                general digital voice interface configuration."
            REVISION "200503150000Z"
            DESCRIPTION 
                "The initial version of this MIB file."
            ::= { hh3cVoice 4 }

        
        hh3cVoDigitalIfCommonObjects OBJECT IDENTIFIER ::= 
                                        { hh3cVoiceDigitalInterface 1 }


--==========================================================================
--                      hh3cVoDigitalIfCommonCfgTable
--
--==========================================================================
        hh3cVoDigitalIfCommonCfgTable OBJECT-TYPE
            SYNTAX SEQUENCE OF HH3CVoDigitalIfCommonCfgEntry
            MAX-ACCESS not-accessible
            STATUS current
            DESCRIPTION
                "This table contains the information about configurable 
                parameters for a digital voice interface."
            ::= { hh3cVoDigitalIfCommonObjects 1 }

        
        hh3cVoDigitalIfCommonCfgEntry OBJECT-TYPE
            SYNTAX HH3CVoDigitalIfCommonCfgEntry
            MAX-ACCESS not-accessible
            STATUS current
            DESCRIPTION
                "The entry of hh3cVoDigitalIfCommonCfgTable, which is 
                automatically created when a digital voice module has 
                been found."
            INDEX { hh3cVoDIfCfgPort, hh3cVoDIfCfgGroup}
            ::= { hh3cVoDigitalIfCommonCfgTable 1 }

        
        HH3CVoDigitalIfCommonCfgEntry ::=
            SEQUENCE { 
                hh3cVoDIfCfgPort
                    Integer32,
                hh3cVoDIfCfgGroup
                    Integer32,
                hh3cVoDIfCfgBoardType
                    INTEGER,
                hh3cVoDIfCfgSignalType
                    INTEGER,
                hh3cVoDIfCfgTsInformation
                    OCTET STRING,
                hh3cVoDIfCfgPortSubLine
                    OCTET STRING
             }

        hh3cVoDIfCfgPort OBJECT-TYPE
            SYNTAX Integer32
            MAX-ACCESS not-accessible
            STATUS current
            DESCRIPTION
                "This object indicates the port of a voice digital module."
            ::= { hh3cVoDigitalIfCommonCfgEntry 1 }


        hh3cVoDIfCfgGroup OBJECT-TYPE
            SYNTAX Integer32
            MAX-ACCESS not-accessible
            STATUS current
            DESCRIPTION
                "This object indicates the group number of a voice digital 
                module."
            ::= { hh3cVoDigitalIfCommonCfgEntry 2 }

        
        hh3cVoDIfCfgBoardType OBJECT-TYPE
            SYNTAX INTEGER
                {
                e1vi(1),
                t1vi(2)
                }
            MAX-ACCESS read-only
            STATUS current
            DESCRIPTION
                "This object indicates the type of board."
            ::= { hh3cVoDigitalIfCommonCfgEntry 3 }

        
        hh3cVoDIfCfgSignalType OBJECT-TYPE
            SYNTAX INTEGER
                {
                r2(1),
                pri(2),
                emImmediateStart(3),
                emDelayStart(4),
                emWinkStart(5)
                }
            MAX-ACCESS read-only
            STATUS current
            DESCRIPTION
                "This object indicates the signal type of a group."
            ::= { hh3cVoDigitalIfCommonCfgEntry 4 }

        
        hh3cVoDIfCfgTsInformation OBJECT-TYPE
            SYNTAX OCTET STRING
            MAX-ACCESS read-only
            STATUS current
            DESCRIPTION
                "This object indicates the availability of every single timeslot 
                for voice services. 
                '1' indicates the timeslot is available for voice services.
                '0' indicates the timeslot is not available for voice services." 
            ::= { hh3cVoDigitalIfCommonCfgEntry 5 }

        hh3cVoDIfCfgPortSubLine OBJECT-TYPE
            SYNTAX OCTET STRING
            MAX-ACCESS read-only
            STATUS current
            DESCRIPTION
                "This object indicates the port subscriber line name."
            ::= { hh3cVoDigitalIfCommonCfgEntry 6 }

        

        hh3cVoDigitalIfEMObjects OBJECT IDENTIFIER ::= 
                                            { hh3cVoiceDigitalInterface 2 }

--==========================================================================
--                      hh3cVoDigitalIfEMCfgTable
--
--==========================================================================
        hh3cVoDigitalIfEMCfgTable OBJECT-TYPE
            SYNTAX SEQUENCE OF HH3CVoDigitalIfEMCfgEntry
            MAX-ACCESS not-accessible
            STATUS current
            DESCRIPTION
                "This table contains the information about configurable 
                parameters for a digital EM voice interface."
            ::= { hh3cVoDigitalIfEMObjects 1 }

        
        hh3cVoDigitalIfEMCfgEntry OBJECT-TYPE
            SYNTAX HH3CVoDigitalIfEMCfgEntry
            MAX-ACCESS not-accessible
            STATUS current
            DESCRIPTION
                "The entry of hh3cVoDigitalIfEMCfgTable."
            INDEX { hh3cVoDIfEMCfgPort, hh3cVoDIfEMCfgGroup }
            ::= { hh3cVoDigitalIfEMCfgTable 1 }

        
        HH3CVoDigitalIfEMCfgEntry ::=
            SEQUENCE { 
                hh3cVoDIfEMCfgPort
                    Integer32,
                hh3cVoDIfEMCfgGroup
                    Integer32,
                hh3cVoDIfEMCfgTimeoutInterDigit
                    Integer32,
                hh3cVoDIfEMCfgTimeoutRinging
                    Integer32,
                hh3cVoDIfEMCfgTimeoutWaitDigit
                    Integer32,
                hh3cVoDIfEMCfgPortSubLine
                    OCTET STRING
             }

        hh3cVoDIfEMCfgPort OBJECT-TYPE
            SYNTAX Integer32
            MAX-ACCESS not-accessible
            STATUS current
            DESCRIPTION
                "This object indicates the port of a voice digital module."
            ::= { hh3cVoDigitalIfEMCfgEntry 1 }

        
        hh3cVoDIfEMCfgGroup OBJECT-TYPE
            SYNTAX Integer32
            MAX-ACCESS not-accessible
            STATUS current
            DESCRIPTION
                "This object indicates the group number of a voice digital 
                module."
            ::= { hh3cVoDigitalIfEMCfgEntry 2 }

        
        hh3cVoDIfEMCfgTimeoutInterDigit OBJECT-TYPE
            SYNTAX Integer32
            MAX-ACCESS read-write
            STATUS current
            DESCRIPTION
                "The maximum seconds, to wait for two DTMF (Dual Tone 
                Multi-Frequency) number."
            ::= { hh3cVoDigitalIfEMCfgEntry 3 }

        
        hh3cVoDIfEMCfgTimeoutRinging OBJECT-TYPE
            SYNTAX Integer32
            MAX-ACCESS read-write
            STATUS current
            DESCRIPTION
                "The maximum seconds, to wait for the ring back on the
                EM interface."
            ::= { hh3cVoDigitalIfEMCfgEntry 4 }

        
        hh3cVoDIfEMCfgTimeoutWaitDigit OBJECT-TYPE
            SYNTAX Integer32
            MAX-ACCESS read-write
            STATUS current
            DESCRIPTION
                "The maximum seconds, to wait for called number of called side."
            ::= { hh3cVoDigitalIfEMCfgEntry 5 }

        hh3cVoDIfEMCfgPortSubLine OBJECT-TYPE
            SYNTAX OCTET STRING
            MAX-ACCESS read-only
            STATUS current
            DESCRIPTION
                "This object indicates the port subscriber line name."
            ::= { hh3cVoDigitalIfEMCfgEntry 6 }


--==========================================================================
--                      hh3cVoDigitalIfEMABCDCfgTable
--
--==========================================================================
        hh3cVoDigitalIfEMABCDCfgTable OBJECT-TYPE
            SYNTAX SEQUENCE OF HH3CVoDigitalIfEMABCDCfgEntry
            MAX-ACCESS not-accessible
            STATUS current
            DESCRIPTION
                "This table contains the information about ABCD bits
                 parameters for a digital EM voice interface."
            ::= { hh3cVoDigitalIfEMObjects 2 }

        
        hh3cVoDigitalIfEMABCDCfgEntry OBJECT-TYPE
            SYNTAX HH3CVoDigitalIfEMABCDCfgEntry
            MAX-ACCESS not-accessible
            STATUS current
            DESCRIPTION
                "The entry of hh3cVoDigitalIfEMABCDCfgTable." 
            INDEX { hh3cVoDIfEMABCDCfgPort, hh3cVoDIfEMABCDCfgGroup }
            ::= { hh3cVoDigitalIfEMABCDCfgTable 1 }

        
        HH3CVoDigitalIfEMABCDCfgEntry ::=
            SEQUENCE { 
                hh3cVoDIfEMABCDCfgPort
                    Integer32,
                hh3cVoDIfEMABCDCfgGroup
                    Integer32,
                hh3cVoDIfEMABCDRxIdle
                    OCTET STRING,
                hh3cVoDIfEMABCDRxSeizure
                    OCTET STRING,
                hh3cVoDIfEMABCDTxIdle
                    OCTET STRING,
                hh3cVoDIfEMABCDTxSeizure
                    OCTET STRING,
                hh3cVoDIFEMABCDSubLine
                    OCTET STRING
             }

        hh3cVoDIfEMABCDCfgPort OBJECT-TYPE
            SYNTAX Integer32
            MAX-ACCESS not-accessible
            STATUS current
            DESCRIPTION
                "This object indicates the port of a voice digital module." 
            ::= { hh3cVoDigitalIfEMABCDCfgEntry 1 }

        
        hh3cVoDIfEMABCDCfgGroup OBJECT-TYPE
            SYNTAX Integer32
            MAX-ACCESS not-accessible
            STATUS current
            DESCRIPTION
                "This object indicates the group number of a voice digital 
                module."
            ::= { hh3cVoDigitalIfEMABCDCfgEntry 2 }

        
        hh3cVoDIfEMABCDRxIdle OBJECT-TYPE
            SYNTAX OCTET STRING (SIZE (4))
            MAX-ACCESS read-write
            STATUS current
            DESCRIPTION
                "This object indicates the ABCD bits of receiving idle 
                signal."
            ::= { hh3cVoDigitalIfEMABCDCfgEntry 3 }

        
        hh3cVoDIfEMABCDRxSeizure OBJECT-TYPE
            SYNTAX OCTET STRING (SIZE (4))
            MAX-ACCESS read-write
            STATUS current
            DESCRIPTION
                "This object indicates the ABCD bits of receiving seizure 
                signal."
            ::= { hh3cVoDigitalIfEMABCDCfgEntry 4 }

        
        hh3cVoDIfEMABCDTxIdle OBJECT-TYPE
            SYNTAX OCTET STRING (SIZE (4))
            MAX-ACCESS read-write
            STATUS current
            DESCRIPTION
                "This object indicates the ABCD bits of sending idle 
                signal."
            ::= { hh3cVoDigitalIfEMABCDCfgEntry 5 }

        
        hh3cVoDIfEMABCDTxSeizure OBJECT-TYPE
            SYNTAX OCTET STRING (SIZE (4))
            MAX-ACCESS read-write
            STATUS current
            DESCRIPTION
                "This object indicates the ABCD bits of sending seizure 
                signal."
            ::= { hh3cVoDigitalIfEMABCDCfgEntry 6 }

        hh3cVoDIFEMABCDSubLine OBJECT-TYPE
            SYNTAX OCTET STRING
            MAX-ACCESS read-only
            STATUS current
            DESCRIPTION
                "This object indicates the port subscriber line name."
            ::= { hh3cVoDigitalIfEMABCDCfgEntry 7 }
            

--==========================================================================
--                      hh3cVoDigitalIfEMTimerTable
--
--==========================================================================
        hh3cVoDigitalIfEMTimerTable OBJECT-TYPE
            SYNTAX SEQUENCE OF HH3CVoDigitalIfEMTimerEntry
            MAX-ACCESS not-accessible
            STATUS current
            DESCRIPTION
                "This table contains the timer parameters for a digital 
                EM voice interface."
        ::= { hh3cVoDigitalIfEMObjects 4 }

        
        hh3cVoDigitalIfEMTimerEntry OBJECT-TYPE
            SYNTAX HH3CVoDigitalIfEMTimerEntry
            MAX-ACCESS not-accessible
            STATUS current
            DESCRIPTION
                "The entry of hh3cVoDigitalIfEMTimerTable." 
            INDEX { hh3cVoDIfEMTimerPort, hh3cVoDIfEMTimerGroup }
            ::= { hh3cVoDigitalIfEMTimerTable 1 }

        
        HH3CVoDigitalIfEMTimerEntry ::=
            SEQUENCE { 
                hh3cVoDIfEMTimerPort
                    Integer32,
                hh3cVoDIfEMTimerGroup
                    Integer32,
                hh3cVoDIfEMTimerSendWink
                    Integer32,
                hh3cVoDIfEMTimerWinkRising
                    Integer32,
                hh3cVoDIfEMTimerWinkHold
                    Integer32,
                hh3cVoDIfEMTimerDialoutDelay
                    Integer32,
                hh3cVoDIfEMTimerDelayRising
                    Integer32,
                hh3cVoDIfEMTimerDelayHold
                    Integer32,
                hh3cVoDIfEMTimerDtmf
                    Integer32,
                hh3cVoDIfEMTimerDtmfInterval
                    Integer32,
                hh3cVoDIfEMTimerPortSubLine
                    OCTET STRING
             }

        hh3cVoDIfEMTimerPort OBJECT-TYPE
            SYNTAX Integer32
            MAX-ACCESS not-accessible
            STATUS current
            DESCRIPTION
                "This object indicates the port of a voice digital module." 
            ::= { hh3cVoDigitalIfEMTimerEntry 1 }

        
        hh3cVoDIfEMTimerGroup OBJECT-TYPE
            SYNTAX Integer32
            MAX-ACCESS not-accessible
            STATUS current
            DESCRIPTION
                "This object indicates the group number of a voice digital 
                module."
            ::= { hh3cVoDigitalIfEMTimerEntry 2 }

        
        hh3cVoDIfEMTimerSendWink OBJECT-TYPE
            SYNTAX Integer32
            MAX-ACCESS read-write
            STATUS current
            DESCRIPTION
                "This object indicates the maximum time in milliseconds
                between receiving seizure signal and sending wink signal. 
                This object can only take effect when hh3cVoDIfCfgSignalType 
                is set to 'emWinkStart'."           
            DEFVAL { 200 }
            ::= { hh3cVoDigitalIfEMTimerEntry 4 }

        
        hh3cVoDIfEMTimerWinkRising OBJECT-TYPE
            SYNTAX Integer32
            MAX-ACCESS read-write
            STATUS current
            DESCRIPTION
                "This object indicates the maximum time in milliseconds
                between sending seizure signal and receiving wink signal. 
                This object can only take effect when hh3cVoDIfCfgSignalType 
                is set to 'emWinkStart'." 
            ::= { hh3cVoDigitalIfEMTimerEntry 5 }

        
        hh3cVoDIfEMTimerWinkHold OBJECT-TYPE
            SYNTAX Integer32
            MAX-ACCESS read-write
            STATUS current
            DESCRIPTION
                "This object indicates the maximum duration in milliseconds
                for sending wink signal. This object can only take effect 
                when hh3cVoDIfCfgSignalType is set to 'emWinkStart'."
            ::= { hh3cVoDigitalIfEMTimerEntry 6 }

        
        hh3cVoDIfEMTimerDialoutDelay OBJECT-TYPE
            SYNTAX Integer32
            MAX-ACCESS read-write
            STATUS current
            DESCRIPTION
                "This object indicates the maximum duration in milliseconds
                for sending called digits. This object can only take effect 
                when hh3cVoDIfCfgSignalType is set to 'emImmediateStart'." 
            ::= { hh3cVoDigitalIfEMTimerEntry 7 }

        
        hh3cVoDIfEMTimerDelayRising OBJECT-TYPE
            SYNTAX Integer32
            MAX-ACCESS read-write
            STATUS current
            DESCRIPTION
                "This object indicates the maximum duration in milliseconds
                between receiveing seizure signal and sending delay signal. 
                This object can only take effect when hh3cVoDIfCfgSignalType 
                is set to 'emDelayStart'." 
            ::= { hh3cVoDigitalIfEMTimerEntry 8 }

        
        hh3cVoDIfEMTimerDelayHold OBJECT-TYPE
            SYNTAX Integer32
            MAX-ACCESS read-write
            STATUS current
            DESCRIPTION
                "This object indicates the maximum duration in milliseconds 
                for sending delay signal. This object can only take effect when 
                hh3cVoDIfCfgSignalType is set to 'emDelayStart'."
            ::= { hh3cVoDigitalIfEMTimerEntry 9 }

        
        hh3cVoDIfEMTimerDtmf OBJECT-TYPE
            SYNTAX Integer32
            MAX-ACCESS read-write
            STATUS current
            DESCRIPTION
                "This object indicates DTMF sending duration in milliseconds." 
            ::= { hh3cVoDigitalIfEMTimerEntry 10 }

        
        hh3cVoDIfEMTimerDtmfInterval OBJECT-TYPE
            SYNTAX Integer32
            MAX-ACCESS read-write
            STATUS current
            DESCRIPTION
                "This object indicates DTMF sending interval in milliseconds."
            ::= { hh3cVoDigitalIfEMTimerEntry 11 }

        hh3cVoDIfEMTimerPortSubLine OBJECT-TYPE
            SYNTAX OCTET STRING
            MAX-ACCESS read-only
            STATUS current
            DESCRIPTION
                "This object indicates the port subscriber line name."
            ::= { hh3cVoDigitalIfEMTimerEntry 12 }
        


        hh3cVoDigitalIfR2Objects OBJECT IDENTIFIER ::= 
                                            { hh3cVoiceDigitalInterface 3 }

--==========================================================================
--                      hh3cVoDigitalIfR2CfgTable
--
--==========================================================================
        hh3cVoDigitalIfR2CfgTable OBJECT-TYPE
            SYNTAX SEQUENCE OF HH3CVoDigitalIfR2CfgEntry
            MAX-ACCESS not-accessible
            STATUS current
            DESCRIPTION
                "This table contains information about general configurable 
                parameters for digital r2 voice interface."
            ::= { hh3cVoDigitalIfR2Objects 1 }

        
        hh3cVoDigitalIfR2CfgEntry OBJECT-TYPE
            SYNTAX HH3CVoDigitalIfR2CfgEntry
            MAX-ACCESS not-accessible
            STATUS current
            DESCRIPTION
                "The entry of hh3cVoDigitalIfR2CfgTable." 
            INDEX { hh3cVoDIfR2CfgPort, hh3cVoDIfR2CfgGroup }
            ::= { hh3cVoDigitalIfR2CfgTable 1 }

        
        HH3CVoDigitalIfR2CfgEntry ::=
            SEQUENCE { 
                hh3cVoDIfR2CfgPort
                    Integer32,
                hh3cVoDIfR2CfgGroup
                    Integer32,
                hh3cVoDIfR2CfgCountryMode
                    INTEGER,
                hh3cVoDIfR2CfgSpecialChar
                    INTEGER,
                hh3cVoDIfR2CfgSpecialSignal
                    Integer32,      
                hh3cVoDIfR2CfgSelectMode
                    INTEGER,
                hh3cVoDIFR2CfgSubLine
                    OCTET STRING
             }

        hh3cVoDIfR2CfgPort OBJECT-TYPE
            SYNTAX Integer32
            MAX-ACCESS not-accessible
            STATUS current
            DESCRIPTION
                "This object indicates the port of a voice digital module." 
            ::= { hh3cVoDigitalIfR2CfgEntry 1 }

        
        hh3cVoDIfR2CfgGroup OBJECT-TYPE
            SYNTAX Integer32
            MAX-ACCESS not-accessible
            STATUS current
            DESCRIPTION
                "This object indicates the group number of a voice digital 
                module."
            ::= { hh3cVoDigitalIfR2CfgEntry 2 }


        hh3cVoDIfR2CfgCountryMode OBJECT-TYPE
            SYNTAX INTEGER 
                {
                customer (1),
                argentina (2),
                australia (3),
                bengal (4),
                brazil (5),
                china (6),
                hongkong (7),
                india (8),
                indonesia (9),
                itut (10),
                korea (11),
                malaysia (12),
                mexico (13),
                newzealand (14),
                singapore (15),
                thailand (16)
                }
            MAX-ACCESS read-write
            STATUS current
            DESCRIPTION
                "This object indicates the value of country mode."
            ::= { hh3cVoDigitalIfR2CfgEntry 3 }
            
            
        hh3cVoDIfR2CfgSpecialChar OBJECT-TYPE
            SYNTAX INTEGER 
                {
                null (0),
                a (65),
                b (66),
                c (67),
                d (68),
                pound (35),
                asterisk (42)
                }
            MAX-ACCESS read-write
            STATUS current
            DESCRIPTION
                "This object indicates the special character(A,B,C,D,#,*)."
            ::= { hh3cVoDigitalIfR2CfgEntry 4 }


        hh3cVoDIfR2CfgSpecialSignal OBJECT-TYPE
            SYNTAX Integer32 (11..16)
            MAX-ACCESS read-write
            STATUS current
            DESCRIPTION
                "This object indicates the signal of special character."
            DEFVAL {16}
            ::= { hh3cVoDigitalIfR2CfgEntry 5 }


        hh3cVoDIfR2CfgSelectMode OBJECT-TYPE
            SYNTAX INTEGER
                {
                min(1),
                max(2),
                minpoll(3),
                maxpoll(4)
                }
            MAX-ACCESS read-write
            STATUS current
            DESCRIPTION
                "This object indicates the trunk mode to be selected:
                min            set selected trunk mode to min-mode.
                max            set selected trunk mode to max-mode.
                minpoll        set selected trunk mode to min-poll-mode.  
                maxpoll        set selected trunk mode to max-poll-mode.
                "
            ::= { hh3cVoDigitalIfR2CfgEntry 6 }

        hh3cVoDIFR2CfgSubLine OBJECT-TYPE
            SYNTAX OCTET STRING
            MAX-ACCESS read-only
            STATUS current
            DESCRIPTION
                "This object indicates the port subscriber line name."
            ::= { hh3cVoDigitalIfR2CfgEntry 7 }
            

--==========================================================================
--                      hh3cVoDigitalIfR2ABCDCfgTable
--
--==========================================================================
        hh3cVoDigitalIfR2ABCDCfgTable OBJECT-TYPE
            SYNTAX SEQUENCE OF HH3CVoDigitalIfR2ABCDCfgEntry
            MAX-ACCESS not-accessible
            STATUS current
            DESCRIPTION
                "This table contains the information about ABCD bits
                 parameters for a digital r2 voice interface."
            ::= { hh3cVoDigitalIfR2Objects 2 }

        
        hh3cVoDigitalIfR2ABCDCfgEntry OBJECT-TYPE
            SYNTAX HH3CVoDigitalIfR2ABCDCfgEntry
            MAX-ACCESS not-accessible
            STATUS current
            DESCRIPTION
                "The entry of hh3cVoDigitalIfR2ABCDCfgTable." 
            INDEX { hh3cVoDIfR2ABCDCfgPort, hh3cVoDIfR2ABCDCfgGroup }
            ::= { hh3cVoDigitalIfR2ABCDCfgTable 1 }

        
        HH3CVoDigitalIfR2ABCDCfgEntry ::=
            SEQUENCE { 
                hh3cVoDIfR2ABCDCfgPort
                    Integer32,
                hh3cVoDIfR2ABCDCfgGroup
                    Integer32,
                hh3cVoDIfR2ABCDReverseABCD
                    OCTET STRING,
                hh3cVoDIfR2ABCDRenewABCD
                    OCTET STRING,
                hh3cVoDIfR2ABCDRxIdle
                    OCTET STRING,
                hh3cVoDIfR2ABCDTxIdle
                    OCTET STRING,
                hh3cVoDIfR2ABCDRxSeizure
                    OCTET STRING,
                hh3cVoDIfR2ABCDTxSeizure
                    OCTET STRING,
                hh3cVoDIfR2ABCDRxSeizureAck
                    OCTET STRING,
                hh3cVoDIfR2ABCDTxSeizureAck
                    OCTET STRING,
                hh3cVoDIfR2ABCDRxAnswer
                    OCTET STRING,
                hh3cVoDIfR2ABCDTxAnswer
                    OCTET STRING,
                hh3cVoDIfR2ABCDRxClearForward
                    OCTET STRING,
                hh3cVoDIfR2ABCDTxClearForward
                    OCTET STRING,
                hh3cVoDIfR2ABCDRxClearBack
                    OCTET STRING,
                hh3cVoDIfR2ABCDTxClearBack
                    OCTET STRING,
                hh3cVoDIfR2ABCDRxReleaseGuard
                    OCTET STRING,
                hh3cVoDIfR2ABCDTxReleaseGuard
                    OCTET STRING,
                hh3cVoDIfR2ABCDRxBlocking
                    OCTET STRING,
                hh3cVoDIfR2ABCDTxBlocking
                    OCTET STRING,
                hh3cVoDIfR2ABCDSubLine
                    OCTET STRING            
             }

        hh3cVoDIfR2ABCDCfgPort OBJECT-TYPE
            SYNTAX Integer32
            MAX-ACCESS not-accessible
            STATUS current
            DESCRIPTION
                "This object indicates the port of a voice digital module."  
            ::= { hh3cVoDigitalIfR2ABCDCfgEntry 1 }

        
        hh3cVoDIfR2ABCDCfgGroup OBJECT-TYPE
            SYNTAX Integer32
            MAX-ACCESS not-accessible
            STATUS current
            DESCRIPTION
                "This object indicates the group number of a voice digital 
                module."
            ::= { hh3cVoDigitalIfR2ABCDCfgEntry 2 }

        
        hh3cVoDIfR2ABCDReverseABCD OBJECT-TYPE
            SYNTAX OCTET STRING (SIZE (4))
            MAX-ACCESS read-write
            STATUS current
            DESCRIPTION
                "This object indicates whether the ABCD bits should be inverted.
                '0' : disable invertion.
                '1' : enable invertion.
                "
            ::= { hh3cVoDigitalIfR2ABCDCfgEntry 3 }

        
        hh3cVoDIfR2ABCDRenewABCD OBJECT-TYPE
            SYNTAX OCTET STRING (SIZE (4))
            MAX-ACCESS read-write
            STATUS current
            DESCRIPTION
                "This object indicates the unused ABCD bits to be sent."
            ::= { hh3cVoDigitalIfR2ABCDCfgEntry 4 }


        hh3cVoDIfR2ABCDRxIdle OBJECT-TYPE
            SYNTAX OCTET STRING (SIZE (4))
            MAX-ACCESS read-write
            STATUS current
            DESCRIPTION
                "This object indicates the IDLE line signaling to be received."
            ::= { hh3cVoDigitalIfR2ABCDCfgEntry 5 }


        hh3cVoDIfR2ABCDTxIdle OBJECT-TYPE
            SYNTAX OCTET STRING (SIZE (4))
            MAX-ACCESS read-write
            STATUS current
            DESCRIPTION
                "This object indicates the IDLE line signaling to be sent."
            ::= { hh3cVoDigitalIfR2ABCDCfgEntry 6 }

        
        hh3cVoDIfR2ABCDRxSeizure OBJECT-TYPE
            SYNTAX OCTET STRING (SIZE (4))
            MAX-ACCESS read-write
            STATUS current
            DESCRIPTION
                "This object indicates the SEIZURE line signaling to be received."
            ::= { hh3cVoDigitalIfR2ABCDCfgEntry 7 }


        hh3cVoDIfR2ABCDTxSeizure OBJECT-TYPE
            SYNTAX OCTET STRING (SIZE (4))
            MAX-ACCESS read-write
            STATUS current
            DESCRIPTION
                "This object indicates the SEIZURE line signaling to be sent."
            ::= { hh3cVoDigitalIfR2ABCDCfgEntry 8 }
    

        hh3cVoDIfR2ABCDRxSeizureAck OBJECT-TYPE
            SYNTAX OCTET STRING (SIZE (4))
            MAX-ACCESS read-write
            STATUS current
            DESCRIPTION
                "This object indicates the SEIZURE_ACK line signaling to be
                received."
            ::= { hh3cVoDigitalIfR2ABCDCfgEntry 9 }


        hh3cVoDIfR2ABCDTxSeizureAck OBJECT-TYPE
            SYNTAX OCTET STRING (SIZE (4))
            MAX-ACCESS read-write
            STATUS current
            DESCRIPTION
                "This object indicates the SEIZURE_ACK line signaling to be sent."
            ::= { hh3cVoDigitalIfR2ABCDCfgEntry 10 }


        hh3cVoDIfR2ABCDRxAnswer OBJECT-TYPE
            SYNTAX OCTET STRING (SIZE (4))
            MAX-ACCESS read-write
            STATUS current
            DESCRIPTION
                "This object indicates the ANSWER line signaling to be received."
            ::= { hh3cVoDigitalIfR2ABCDCfgEntry 11 }


        hh3cVoDIfR2ABCDTxAnswer OBJECT-TYPE
            SYNTAX OCTET STRING (SIZE (4))
            MAX-ACCESS read-write
            STATUS current
            DESCRIPTION
                "This object indicates the ANSWER line signaling to be sent."
            ::= { hh3cVoDigitalIfR2ABCDCfgEntry 12 }


        hh3cVoDIfR2ABCDRxClearForward OBJECT-TYPE
            SYNTAX OCTET STRING (SIZE (4))
            MAX-ACCESS read-write
            STATUS current
            DESCRIPTION
                "This object indicates the CLEAR_FORWARD line signaling to be
                received."
            ::= { hh3cVoDigitalIfR2ABCDCfgEntry 13 }


        hh3cVoDIfR2ABCDTxClearForward OBJECT-TYPE
            SYNTAX OCTET STRING (SIZE (4))
            MAX-ACCESS read-write
            STATUS current
            DESCRIPTION
                "This object indicates the CLEAR_FORWARD line signaling to 
                be sent." 
            ::= { hh3cVoDigitalIfR2ABCDCfgEntry 14 }


        hh3cVoDIfR2ABCDRxClearBack OBJECT-TYPE
            SYNTAX OCTET STRING (SIZE (4))
            MAX-ACCESS read-write
            STATUS current
            DESCRIPTION
                "This object indicates the CLEAR_BACKWARD line signaling to
                be received."
            ::= { hh3cVoDigitalIfR2ABCDCfgEntry 15 }


        hh3cVoDIfR2ABCDTxClearBack OBJECT-TYPE
            SYNTAX OCTET STRING (SIZE (4))
            MAX-ACCESS read-write
            STATUS current
            DESCRIPTION
                "This object indicates the CLEAR_BACKWARD line signaling to
                be sent."
            ::= { hh3cVoDigitalIfR2ABCDCfgEntry 16 }


        hh3cVoDIfR2ABCDRxReleaseGuard OBJECT-TYPE
            SYNTAX OCTET STRING (SIZE (4))
            MAX-ACCESS read-write
            STATUS current
            DESCRIPTION
                "This object indicates the RELEASE_GUARD line signaling 
                to be received."
            ::= { hh3cVoDigitalIfR2ABCDCfgEntry 17 }


        hh3cVoDIfR2ABCDTxReleaseGuard OBJECT-TYPE
            SYNTAX OCTET STRING (SIZE (4))
            MAX-ACCESS read-write
            STATUS current
            DESCRIPTION
                "This object indicates the RELEASE_GUARD line signaling
                to be sent."
            ::= { hh3cVoDigitalIfR2ABCDCfgEntry 18 }

            
        hh3cVoDIfR2ABCDRxBlocking OBJECT-TYPE
            SYNTAX OCTET STRING (SIZE (4))
            MAX-ACCESS read-write
            STATUS current
            DESCRIPTION
                "This object indicates the BLOCKING line signaling to be 
                received."
            ::= { hh3cVoDigitalIfR2ABCDCfgEntry 19 }


        hh3cVoDIfR2ABCDTxBlocking OBJECT-TYPE
            SYNTAX OCTET STRING (SIZE (4))
            MAX-ACCESS read-write
            STATUS current
            DESCRIPTION
                "This object indicates the BLOCKING line signaling to be
                sent."
            ::= { hh3cVoDigitalIfR2ABCDCfgEntry 20}


        hh3cVoDIfR2ABCDSubLine OBJECT-TYPE
            SYNTAX OCTET STRING
            MAX-ACCESS read-only
            STATUS current
            DESCRIPTION
                "This object indicates the port subscriber line name."
            ::= { hh3cVoDigitalIfR2ABCDCfgEntry 21 }


--==========================================================================
--                      hh3cVoDigitalIfR2MfcCfgTable
--
--==========================================================================
        hh3cVoDigitalIfR2MfcCfgTable OBJECT-TYPE
            SYNTAX SEQUENCE OF HH3CVoDigitalIfR2MfcCfgEntry
            MAX-ACCESS not-accessible
            STATUS current
            DESCRIPTION
                "This table contains information about MFC(Multi-Frequency  
                Control) configurable parameters for digital r2 voice 
                interface."
            ::= { hh3cVoDigitalIfR2Objects 3 }

        
        hh3cVoDigitalIfR2MfcCfgEntry OBJECT-TYPE
            SYNTAX HH3CVoDigitalIfR2MfcCfgEntry
            MAX-ACCESS not-accessible
            STATUS current
            DESCRIPTION
                "The entry of hh3cVoDigitalIfR2MfcCfgTable." 
            INDEX { hh3cVoDIfR2MfcCfgPort, hh3cVoDIfR2MfcCfgGroup }
            ::= { hh3cVoDigitalIfR2MfcCfgTable 1 }

        
        HH3CVoDigitalIfR2MfcCfgEntry ::=
            SEQUENCE { 
                hh3cVoDIfR2MfcCfgPort
                    Integer32,
                hh3cVoDIfR2MfcCfgGroup
                    Integer32,
                hh3cVoDIfR2BillingCategory
                    Integer32,
                hh3cVoDIfR2CallingCategory
                    Integer32,      
                hh3cVoDIfR2Congestion
                    Integer32,  
                hh3cVoDIfR2DemandRefused
                    Integer32,                                          
                hh3cVoDIfR2DigitEnd
                    Integer32,  
                hh3cVoDIfR2Nullnum
                    Integer32,  
                hh3cVoDIfR2ReqBillingCategory
                    Integer32,
                hh3cVoDIfR2ReqCallingCategory
                    Integer32,
                hh3cVoDIfR2ReqCurrentdigit
                    Integer32,
                hh3cVoDIfR2ReqFirstCallingnum
                    Integer32,
                hh3cVoDIfR2ReqFirstDigit
                    Integer32,
                hh3cVoDIfR2ReqNextCallednum
                    Integer32,
                hh3cVoDIfR2ReqNextCallingnum
                    Integer32,
                hh3cVoDIfR2ReqLastFirstDigit
                    Integer32,
                hh3cVoDIfR2ReqLastSecondDigit
                    Integer32,
                hh3cVoDIfR2ReqLastThirdDigit
                    Integer32,
                hh3cVoDIfR2ReqSwitchGroupB
                    Integer32,
                hh3cVoDIfR2SubscriberIdle
                    Integer32,
                hh3cVoDIfR2SubscriberBusy
                    Integer32,
                hh3cVoDIfR2ReqCallingnumOffset
                    Integer32,
                hh3cVoDIfR2CallCreateInA
                    Integer32,
                hh3cVoDIfR2ReqFirstCalledNumInC
                    Integer32,
                hh3cVoDIfR2ReqCurCalledNumInC
                    Integer32,
                hh3cVoDIfR2ReqCalledNumSwitchA
                    Integer32,
                hh3cVoDIfR2ReqSpecialSignal
                    Integer32,
                hh3cVoDIfR2SubscriberCharge
                    Integer32,
                hh3cVoDIfR2SubscriberAbnormal
                    Integer32,
                hh3cVoDIfR2Ani
                    INTEGER,
                hh3cVoDIfR2SubLine
                    OCTET STRING
             }

        hh3cVoDIfR2MfcCfgPort OBJECT-TYPE
            SYNTAX Integer32
            MAX-ACCESS not-accessible
            STATUS current
            DESCRIPTION
                "This object indicates the port of a voice digital module."  
            ::= { hh3cVoDigitalIfR2MfcCfgEntry 1 }

        
        hh3cVoDIfR2MfcCfgGroup OBJECT-TYPE
            SYNTAX Integer32
            MAX-ACCESS not-accessible
            STATUS current
            DESCRIPTION
                "This object indicates the group number of a voice digital 
                module."
            ::= { hh3cVoDigitalIfR2MfcCfgEntry 2 }

        hh3cVoDIfR2BillingCategory OBJECT-TYPE
            SYNTAX Integer32 (1..16)
            MAX-ACCESS read-write
            STATUS current
            DESCRIPTION
                "This object indicates the value of BILLING CATEGORY during
                the MFC procedure."
            ::= { hh3cVoDigitalIfR2MfcCfgEntry 3 }           
            
                            
        hh3cVoDIfR2CallingCategory OBJECT-TYPE
            SYNTAX Integer32 (1..16)
            MAX-ACCESS read-write
            STATUS current
            DESCRIPTION
                "This object indicates the value of CALLING CATEGORY during 
                the MFC procedure."
            ::= { hh3cVoDigitalIfR2MfcCfgEntry 4 }
        
        
        hh3cVoDIfR2Congestion OBJECT-TYPE
            SYNTAX Integer32 (1..16)
            MAX-ACCESS read-write
            STATUS current
            DESCRIPTION
                "This object indicates the value of CONGESTION during 
                the MFC procedure. "
            ::= { hh3cVoDigitalIfR2MfcCfgEntry 5 }


        hh3cVoDIfR2DemandRefused OBJECT-TYPE
            SYNTAX Integer32 (1..16)
            MAX-ACCESS read-write
            STATUS current
            DESCRIPTION
                "This object indicates the value of DEMAND REFUSED during 
                the MFC procedure."
            ::= { hh3cVoDigitalIfR2MfcCfgEntry 6 }


        hh3cVoDIfR2DigitEnd OBJECT-TYPE
            SYNTAX Integer32 (1..16)
            MAX-ACCESS read-write
            STATUS current
            DESCRIPTION
                "This object indicates the value of DIGIT END during 
                the MFC procedure."
            ::= { hh3cVoDigitalIfR2MfcCfgEntry 7 }


        hh3cVoDIfR2Nullnum OBJECT-TYPE
            SYNTAX Integer32 (1..16)
            MAX-ACCESS read-write
            STATUS current
            DESCRIPTION
                "This object indicates the value of NULL NUMBER during 
                the MFC procedure."
            ::= { hh3cVoDigitalIfR2MfcCfgEntry 8 }


        hh3cVoDIfR2ReqBillingCategory OBJECT-TYPE
            SYNTAX Integer32 (1..16)
            MAX-ACCESS read-write
            STATUS current
            DESCRIPTION
                "This object indicates the value of REQUESTING BILLING 
                category during the MFC procedure."
            ::= { hh3cVoDigitalIfR2MfcCfgEntry 9 }


        hh3cVoDIfR2ReqCallingCategory OBJECT-TYPE
            SYNTAX Integer32 (1..16)
            MAX-ACCESS read-write
            STATUS current
            DESCRIPTION
                "This object indicates the value of REQUESTING CALLING CATEGORY 
                during the MFC procedure."
            ::= { hh3cVoDigitalIfR2MfcCfgEntry 10 }


        hh3cVoDIfR2ReqCurrentdigit OBJECT-TYPE
            SYNTAX Integer32 (1..16)
            MAX-ACCESS read-write
            STATUS current
            DESCRIPTION
                "This object indicates the value of REQUESTING CURRENT DIGIT 
                during the MFC procedure."
            ::= { hh3cVoDigitalIfR2MfcCfgEntry 11 }


        hh3cVoDIfR2ReqFirstCallingnum OBJECT-TYPE
            SYNTAX Integer32 (1..16)
            MAX-ACCESS read-write
            STATUS current
            DESCRIPTION
                "This object indicates the value of REQUESTING FIRST CALLING 
                NUMBER during the MFC procedure."
            ::= { hh3cVoDigitalIfR2MfcCfgEntry 12 }


        hh3cVoDIfR2ReqFirstDigit OBJECT-TYPE
            SYNTAX Integer32 (1..16)
            MAX-ACCESS read-write
            STATUS current
            DESCRIPTION
                "This object indicates the value of REQUESTING FIRST DIGIT 
                during the MFC procedure."
            ::= { hh3cVoDigitalIfR2MfcCfgEntry 13 }


        hh3cVoDIfR2ReqNextCallednum OBJECT-TYPE
            SYNTAX Integer32 (1..16)
            MAX-ACCESS read-write
            STATUS current
            DESCRIPTION
                "This object indicates the value of REQUESTING NEXT CALLED 
                NUMBER during the MFC procedure."
            ::= { hh3cVoDigitalIfR2MfcCfgEntry 14 }

        hh3cVoDIfR2ReqNextCallingnum OBJECT-TYPE
            SYNTAX Integer32 (1..16)
            MAX-ACCESS read-write
            STATUS current
            DESCRIPTION
                "This object indicates the value of REQUESTING NEXT CALLING 
                NUMBER during the MFC procedure."
            ::= { hh3cVoDigitalIfR2MfcCfgEntry 15 }

        hh3cVoDIfR2ReqLastFirstDigit OBJECT-TYPE
            SYNTAX Integer32 (1..16)
            MAX-ACCESS read-write
            STATUS current
            DESCRIPTION
                "This object indicates the value of REQUESTING LAST FIRST 
                DIGIT during the MFC procedure."
            ::= { hh3cVoDigitalIfR2MfcCfgEntry 16 }

        hh3cVoDIfR2ReqLastSecondDigit OBJECT-TYPE
            SYNTAX Integer32 (1..16)
            MAX-ACCESS read-write
            STATUS current
            DESCRIPTION
                "This object indicates the value of REQUESTING LAST SECOND DIIGT 
                during the MFC procedure."
            ::= { hh3cVoDigitalIfR2MfcCfgEntry 17 }

        hh3cVoDIfR2ReqLastThirdDigit OBJECT-TYPE
            SYNTAX Integer32 (1..16)
            MAX-ACCESS read-write
            STATUS current
            DESCRIPTION
                "This object indicates the value of REQUESTING LAST LAST THIRD 
                DIGIT during the MFC procedure."
            ::= { hh3cVoDigitalIfR2MfcCfgEntry 18 }

        hh3cVoDIfR2ReqSwitchGroupB OBJECT-TYPE
            SYNTAX Integer32 (1..16)
            MAX-ACCESS read-write
            STATUS current
            DESCRIPTION
                "This object indicates the value of REQUESTING SWITCH GROUP B 
                during the MFC procedure."
            ::= { hh3cVoDigitalIfR2MfcCfgEntry 19 }

        hh3cVoDIfR2SubscriberIdle OBJECT-TYPE
            SYNTAX Integer32 (1..16)
            MAX-ACCESS read-write
            STATUS current
            DESCRIPTION
                "This object indicates the value of SUSCRIBER IDLE during the 
                MFC procedure."
            ::= { hh3cVoDigitalIfR2MfcCfgEntry 20 }

        hh3cVoDIfR2SubscriberBusy OBJECT-TYPE
            SYNTAX Integer32 (1..16)
            MAX-ACCESS read-write
            STATUS current
            DESCRIPTION
                "This object indicates the value of SUBSCRIBER BUSY."
            ::= { hh3cVoDigitalIfR2MfcCfgEntry 21 }

        hh3cVoDIfR2ReqCallingnumOffset OBJECT-TYPE
            SYNTAX Integer32 (1..10)
            MAX-ACCESS read-write
            STATUS current
            DESCRIPTION
                "This object indicates the value of CALLING NUMBER OFFSET 
                during the MFC procedure."
            ::= { hh3cVoDigitalIfR2MfcCfgEntry 22 }
            
        hh3cVoDIfR2CallCreateInA OBJECT-TYPE
            SYNTAX Integer32 (1..16)
            MAX-ACCESS read-write
            STATUS current
            DESCRIPTION
                "This object indicates the value of CALLCREATE IN GROUP A during 
                the MFC procedure.
                "
        DEFVAL {6}
            ::= { hh3cVoDigitalIfR2MfcCfgEntry 23 }

        hh3cVoDIfR2ReqFirstCalledNumInC OBJECT-TYPE
            SYNTAX Integer32 (1..16)
            MAX-ACCESS read-write
            STATUS current
            DESCRIPTION
                "This object indicates the value of FIRST CALLED NUMBER IN GROUP C 
                during the MFC procedure."
            ::= { hh3cVoDigitalIfR2MfcCfgEntry 24 }
            
        hh3cVoDIfR2ReqCurCalledNumInC OBJECT-TYPE
            SYNTAX Integer32 (1..16)
            MAX-ACCESS read-write
            STATUS current
            DESCRIPTION
                "This object indicates the value of CURRENT CALLED NUMBER IN GROUP 
                C during the MFC procedure."
            ::= { hh3cVoDigitalIfR2MfcCfgEntry 25 }
            
        hh3cVoDIfR2ReqCalledNumSwitchA OBJECT-TYPE
            SYNTAX Integer32 (1..16)
            MAX-ACCESS read-write
            STATUS current
            DESCRIPTION
                "This object indicates the value of REQUEST CALLED NUMBER AND 
                SWITCH TO GROUP A during the MFC procedure."
            ::= { hh3cVoDigitalIfR2MfcCfgEntry 26 }
            
        hh3cVoDIfR2ReqSpecialSignal OBJECT-TYPE
            SYNTAX Integer32 (1..16)
            MAX-ACCESS read-write
            STATUS current
            DESCRIPTION
                "This object indicates the value of SPECIAL SIGNAL during the 
                MFC procedure."
            ::= { hh3cVoDigitalIfR2MfcCfgEntry 27 }
        
        hh3cVoDIfR2SubscriberCharge OBJECT-TYPE
            SYNTAX Integer32 (1..16)
            MAX-ACCESS read-write
            STATUS current
            DESCRIPTION
                "This object indicates the value of SUBSCRIBER CHARGE during the 
                MFC procedure."
            ::= { hh3cVoDigitalIfR2MfcCfgEntry 28 }

        hh3cVoDIfR2SubscriberAbnormal OBJECT-TYPE
            SYNTAX Integer32 (1..16)
            MAX-ACCESS read-write
            STATUS current
            DESCRIPTION
                "This object indicates the value of SUBSCRIBER ABNORMAL during 
                the MFC procedure."
            ::= { hh3cVoDigitalIfR2MfcCfgEntry 29 }
            
        hh3cVoDIfR2Ani OBJECT-TYPE
            SYNTAX INTEGER
                {
                disable(1),
                all(2),
                ka(3)
                }
            MAX-ACCESS read-write
            STATUS current
            DESCRIPTION
                "This object indicates whether to return the calling category and 
                the call number during the MFC procedure." 
            ::= { hh3cVoDigitalIfR2MfcCfgEntry 30 }
            
        hh3cVoDIfR2SubLine OBJECT-TYPE
            SYNTAX OCTET STRING 
            MAX-ACCESS read-only
            STATUS current
            DESCRIPTION
                "This object indicates the port subscriber line name."
            ::= { hh3cVoDigitalIfR2MfcCfgEntry 31 }



--==========================================================================
--                      hh3cVoDigitalIfR2TimerCfgTable
--
--==========================================================================
        hh3cVoDigitalIfR2TimerCfgTable OBJECT-TYPE
            SYNTAX SEQUENCE OF HH3CVoDigitalIfR2TimerCfgEntry
            MAX-ACCESS not-accessible
            STATUS current
            DESCRIPTION
                "This table contains information about time parameters
                for digital r2 voice interface."
            ::= { hh3cVoDigitalIfR2Objects 4 }

        
        hh3cVoDigitalIfR2TimerCfgEntry OBJECT-TYPE
            SYNTAX HH3CVoDigitalIfR2TimerCfgEntry
            MAX-ACCESS not-accessible
            STATUS current
            DESCRIPTION
                "The entry of hh3cVoDigitalIfR2TimeCfgTable." 
            INDEX { hh3cVoDIfR2TimeCfgPort, hh3cVoDIfR2TimeCfgGroup }
            ::= { hh3cVoDigitalIfR2TimerCfgTable 1 }

        
        HH3CVoDigitalIfR2TimerCfgEntry ::=
            SEQUENCE { 
                hh3cVoDIfR2TimeCfgPort
                    Integer32,
                hh3cVoDIfR2TimeCfgGroup
                    Integer32,
                hh3cVoDIfR2CfgDebounceTime
                    Integer32,      
                hh3cVoDIfR2CfgSendringBackTime
                    Integer32,  
                hh3cVoDIfR2CfgSendringBusyTime
                    Integer32,                                                                  
                hh3cVoDIfR2PulseSignalPersistT
                    Integer32,
                hh3cVoDIfR2CfgDlAnswerTime
                    Integer32,
                hh3cVoDIfR2CfgDlClearBackTime
                    Integer32,
                hh3cVoDIfR2CfgDlClearForwardT
                    Integer32,
                hh3cVoDIfR2CfgDlSeizureTime
                    Integer32,
                hh3cVoDIfR2CfgDlReanswerTime
                    Integer32,
                hh3cVoDIfR2CfgDlRelGuardTime
                    Integer32,
                hh3cVoDIfR2CfgMfcGroupBTime
                    Integer32,
                hh3cVoDIfR2CfgDTMFTime
                    Integer32,
                hh3cVoDIfR2TimeCfgSubLine
                    OCTET STRING
             }

        hh3cVoDIfR2TimeCfgPort OBJECT-TYPE
            SYNTAX Integer32
            MAX-ACCESS not-accessible
            STATUS current
            DESCRIPTION
                "This object indicates the port of a voice digital module."  
            ::= { hh3cVoDigitalIfR2TimerCfgEntry 1 }
                  
        
        hh3cVoDIfR2TimeCfgGroup OBJECT-TYPE
            SYNTAX Integer32
            MAX-ACCESS not-accessible
            STATUS current
            DESCRIPTION
                "This object indicates the group number of a voice digital 
                module."
            ::= { hh3cVoDigitalIfR2TimerCfgEntry 2 }

        hh3cVoDIfR2CfgDebounceTime OBJECT-TYPE
            SYNTAX Integer32
            MAX-ACCESS read-write
            STATUS current
            DESCRIPTION
                "This object indicates the minimum duration which is the line 
                signal going to persist."
            ::= { hh3cVoDigitalIfR2TimerCfgEntry 3 }
            
            
        hh3cVoDIfR2CfgSendringBackTime OBJECT-TYPE
            SYNTAX Integer32
            MAX-ACCESS read-write
            STATUS current
            DESCRIPTION
                "This object indicates the minimum duration which is the ring 
                back going to persist."
            ::= { hh3cVoDigitalIfR2TimerCfgEntry 4 }
            
            
        hh3cVoDIfR2CfgSendringBusyTime OBJECT-TYPE
            SYNTAX Integer32
            MAX-ACCESS read-write
            STATUS current
            DESCRIPTION
                "This object indicates the minimum duration which is the ring 
                busy going to persist."
            ::= { hh3cVoDigitalIfR2TimerCfgEntry 5 }
        
        
        hh3cVoDIfR2PulseSignalPersistT OBJECT-TYPE
            SYNTAX Integer32
            MAX-ACCESS read-write
            STATUS current
            DESCRIPTION
                "This object indicates the value of pulse signal persistence 
                timer."
            ::= { hh3cVoDigitalIfR2TimerCfgEntry 6 }

        hh3cVoDIfR2CfgDlAnswerTime OBJECT-TYPE
            SYNTAX Integer32
            MAX-ACCESS read-write
            STATUS current
            DESCRIPTION
                "This object indicates the value of answer timer."
            ::= { hh3cVoDigitalIfR2TimerCfgEntry 7 }

        hh3cVoDIfR2CfgDlClearBackTime OBJECT-TYPE
            SYNTAX Integer32
            MAX-ACCESS read-write
            STATUS current
            DESCRIPTION
                "This object indicates the value of clear back timer."
            ::= { hh3cVoDigitalIfR2TimerCfgEntry 8 }

        hh3cVoDIfR2CfgDlClearForwardT OBJECT-TYPE
            SYNTAX Integer32
            MAX-ACCESS read-write
            STATUS current
            DESCRIPTION
                "This object indicates the value of clear forward timer."
            ::= { hh3cVoDigitalIfR2TimerCfgEntry 9 }

        hh3cVoDIfR2CfgDlSeizureTime OBJECT-TYPE
            SYNTAX Integer32
            MAX-ACCESS read-write
            STATUS current
            DESCRIPTION
                "This object indicates the value of seizure timer."
            ::= { hh3cVoDigitalIfR2TimerCfgEntry 10 }

        hh3cVoDIfR2CfgDlReanswerTime OBJECT-TYPE
            SYNTAX Integer32
            MAX-ACCESS read-write
            STATUS current
            DESCRIPTION
                "This object indicates the value of reanswer timer."
            ::= { hh3cVoDigitalIfR2TimerCfgEntry 11 }

        hh3cVoDIfR2CfgDlRelGuardTime OBJECT-TYPE
            SYNTAX Integer32
            MAX-ACCESS read-write
            STATUS current
            DESCRIPTION
                "This object indicates the value of release guard timer."
            ::= { hh3cVoDigitalIfR2TimerCfgEntry 12 }

        hh3cVoDIfR2CfgMfcGroupBTime OBJECT-TYPE
            SYNTAX Integer32
            MAX-ACCESS read-write
            STATUS current
            DESCRIPTION
                "This object indicates the value of group B timer."
            ::= { hh3cVoDigitalIfR2TimerCfgEntry 13 }

        hh3cVoDIfR2CfgDTMFTime OBJECT-TYPE
            SYNTAX Integer32
            MAX-ACCESS read-write
            STATUS current
            DESCRIPTION
                "This object indicates the value of DTMF(Dual Tone 
                Multi-Frequency) timer."
            ::= { hh3cVoDigitalIfR2TimerCfgEntry 14 }

        hh3cVoDIfR2TimeCfgSubLine OBJECT-TYPE
            SYNTAX OCTET STRING 
            MAX-ACCESS read-only
            STATUS current
            DESCRIPTION
                "This object indicates the port subscriber line name."
            ::= { hh3cVoDigitalIfR2TimerCfgEntry 15 }


--==========================================================================
--                      hh3cVoDIfR2CapabilityCfgTable
--
--==========================================================================
        hh3cVoDIfR2CapabilityCfgTable OBJECT-TYPE
            SYNTAX SEQUENCE OF HH3CVoDIfR2CapabilityCfgEntry
            MAX-ACCESS not-accessible
            STATUS current
            DESCRIPTION
                "This table contains information about capability parameters
                for digital r2 voice interface."
            ::= { hh3cVoDigitalIfR2Objects 5 }

        
        hh3cVoDIfR2CapabilityCfgEntry OBJECT-TYPE
            SYNTAX HH3CVoDIfR2CapabilityCfgEntry
            MAX-ACCESS not-accessible
            STATUS current
            DESCRIPTION
                "The entry of hh3cVoDIfR2CapabilityCfgTable." 
            INDEX { hh3cVoDIfR2CapCfgPort, hh3cVoDIfR2CapCfgGroup }
            ::= { hh3cVoDIfR2CapabilityCfgTable 1 }

        
        HH3CVoDIfR2CapabilityCfgEntry ::=
            SEQUENCE { 
                hh3cVoDIfR2CapCfgPort
                    Integer32,
                hh3cVoDIfR2CapCfgGroup
                    Integer32,
                hh3cVoDIfR2CfgGroupB
                    INTEGER,
                hh3cVoDIfR2CfgClearForwardAck
                    INTEGER,
                hh3cVoDIfR2CfgDlSeizureAck
                    INTEGER,    
                hh3cVoDIfR2CfgDTMF
                    INTEGER,
                hh3cVoDIfR2CfgAnswer
                    INTEGER,
                hh3cVoDIfR2CfgReanswer
                    INTEGER,    
                hh3cVoDIfR2CfgFinalCallnum
                    INTEGER,
                hh3cVoDIfR2CfgForceMetering
                    INTEGER,
                hh3cVoDIfR2CfgSendRingBack
                    INTEGER,
                hh3cVoDIfR2CfgSendRingBusy
                    INTEGER,
                hh3cVoDIfR2CapCfgSubLine
                    OCTET STRING
             }

        hh3cVoDIfR2CapCfgPort OBJECT-TYPE
            SYNTAX Integer32
            MAX-ACCESS not-accessible
            STATUS current
            DESCRIPTION
                "This object indicates the port of a voice digital module."  
            ::= { hh3cVoDIfR2CapabilityCfgEntry 1 }
        
        hh3cVoDIfR2CapCfgGroup OBJECT-TYPE
            SYNTAX Integer32
            MAX-ACCESS not-accessible
            STATUS current
            DESCRIPTION
                "This object indicates the group number of a voice digital module."
            ::= { hh3cVoDIfR2CapabilityCfgEntry 2 }

        hh3cVoDIfR2CfgGroupB OBJECT-TYPE
            SYNTAX INTEGER
                {
                enable(1),
                disable(2)
                }
            MAX-ACCESS read-write
            STATUS current
            DESCRIPTION
                "This object indicates whether the group B process is enabled."
            ::= { hh3cVoDIfR2CapabilityCfgEntry 3 }

        hh3cVoDIfR2CfgClearForwardAck OBJECT-TYPE
            SYNTAX INTEGER
                {
                enable(1),
                disable(2)
                }
            MAX-ACCESS read-write
            STATUS current
            DESCRIPTION
                "This object indicates whether the CLEAR_FORWARD_ACK signal is 
                enabled."
            ::= { hh3cVoDIfR2CapabilityCfgEntry 4 }

        hh3cVoDIfR2CfgDlSeizureAck OBJECT-TYPE
            SYNTAX INTEGER
                {
                enable(1),
                disable(2)
                }
            MAX-ACCESS read-write
            STATUS current
            DESCRIPTION
                "This object indicates whether the SEIZURE_ACK signal is enabled."
            ::= { hh3cVoDIfR2CapabilityCfgEntry 5 }

        hh3cVoDIfR2CfgDTMF OBJECT-TYPE
            SYNTAX INTEGER
                {
                enable(1),
                disable(2)
                }
            MAX-ACCESS read-write
            STATUS current
            DESCRIPTION
                "This object indicates whether the DTMF(Dual Tone Multi-Frequency) 
                is enabled."
            ::= { hh3cVoDIfR2CapabilityCfgEntry 6 }

        hh3cVoDIfR2CfgAnswer OBJECT-TYPE
            SYNTAX INTEGER
                {
                enable(1),
                disable(2)
                }
            MAX-ACCESS read-write
            STATUS current
            DESCRIPTION
                "This object indicates whether the ANSWER signal is enabled."
            ::= { hh3cVoDIfR2CapabilityCfgEntry 7 }

        hh3cVoDIfR2CfgReanswer OBJECT-TYPE
            SYNTAX INTEGER
                {
                enable(1),
                disable(2)
                }
            MAX-ACCESS read-write
            STATUS current
            DESCRIPTION
                "This object indicates whether the REANSWER signal is enabled."
            ::= { hh3cVoDIfR2CapabilityCfgEntry 8 } 

        hh3cVoDIfR2CfgFinalCallnum OBJECT-TYPE
            SYNTAX INTEGER
                {
                enable(1),
                disable(2)
                }
            MAX-ACCESS read-write
            STATUS current
            DESCRIPTION
                "This object indicates whether the FINAL_CALL_NUMBER signal 
                is enabled."
            ::= { hh3cVoDIfR2CapabilityCfgEntry 9 }

        hh3cVoDIfR2CfgForceMetering OBJECT-TYPE
            SYNTAX INTEGER
                {
                enable(1),
                disable(2)
                }
            MAX-ACCESS read-write
            STATUS current
            DESCRIPTION
                "This object indicates whether the METERING signal is enabled."
            ::= { hh3cVoDIfR2CapabilityCfgEntry 10 }

        hh3cVoDIfR2CfgSendRingBack OBJECT-TYPE
            SYNTAX INTEGER
                {
                enable(1),
                disable(2)
                }
            MAX-ACCESS read-write
            STATUS current
            DESCRIPTION
                "This object indicates whether to send the ring back tone."
            ::= { hh3cVoDIfR2CapabilityCfgEntry 11 }

        hh3cVoDIfR2CfgSendRingBusy OBJECT-TYPE
            SYNTAX INTEGER
                {
                enable(1),
                disable(2)
                }
            MAX-ACCESS read-write
            STATUS current
            DESCRIPTION
                "This object indicates whether to send the busy tone."
            ::= { hh3cVoDIfR2CapabilityCfgEntry 12 }

        hh3cVoDIfR2CapCfgSubLine OBJECT-TYPE
            SYNTAX OCTET STRING 
            MAX-ACCESS read-only
            STATUS current
            DESCRIPTION
                "This object indicates the port subscriber line name."
            ::= { hh3cVoDIfR2CapabilityCfgEntry 15 }

    END
