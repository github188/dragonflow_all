NEUSOFT-MIB DEFINITIONS ::=BEGIN

		IMPORTS
			enterprises, Integer32, OBJECT-TYPE
				FROM SNMPv2-SMI;
	DisplayString ::= OCTET STRING
--
-- Node definitions
--

		-- 1.3.6.1.4.1.8596
		neusoft OBJECT IDENTIFIER ::={ enterprises 8596 }

		-- 1.3.6.1.4.1.8596.1
		neusoftFirewall OBJECT IDENTIFIER ::={ neusoft 1 }

		-- 1.3.6.1.4.1.8596.1.1
		fwSystemInfo OBJECT IDENTIFIER ::={ neusoftFirewall 1 }

		-- 1.3.6.1.4.1.8596.1.1.1
		fwProductName OBJECT-TYPE
			SYNTAX DisplayString (SIZE(0..255))
			MAX-ACCESS read-only
			STATUS current
			DESCRIPTION
				"Neusoft firewall product name, e.g. NetEye Firewall."
			::={ fwSystemInfo 1 }

		-- 1.3.6.1.4.1.8596.1.1.2
		fwProductVer OBJECT-TYPE
			SYNTAX DisplayString (SIZE(0..255))
			MAX-ACCESS read-only
			STATUS current
			DESCRIPTION
				"Neusoft firewall product version, e.g. 3.2.1 ."
			::={ fwSystemInfo 2 }

		-- 1.3.6.1.4.1.8596.1.1.3
		fwRegMsg OBJECT-TYPE
			SYNTAX DisplayString (SIZE(0..255))
			MAX-ACCESS read-only
			STATUS current
			DESCRIPTION
				"Firewall Reg Message."
			::={ fwSystemInfo 3 } 
		
		-- 1.3.6.1.4.1.8596.1.1.4
		fwName OBJECT-TYPE
			SYNTAX DisplayString (SIZE(0..255) )
			MAX-ACCESS read-write
			STATUS current
			DESCRIPTION
				"Host Name."
			::={ fwSystemInfo 4 } 
		
		-- 1.3.6.1.4.1.8596.1.2
		fwRunStat OBJECT IDENTIFIER ::={neusoftFirewall 2}

		-- 1.3.6.1.4.1.8596.1.2.1
		fwCpuUsage OBJECT-TYPE
			SYNTAX Integer32 (0..100)
			MAX-ACCESS read-only
			STATUS current
			DESCRIPTION
				"System CPU usage(%)."
			::= { fwRunStat 1 }

		-- 1.3.6.1.4.1.8596.1.2.2
		fwMemUsage OBJECT-TYPE
			SYNTAX Integer32 (0..100)
			MAX-ACCESS read-only
			STATUS current
			DESCRIPTION
				"System Memory usage(%)."
			::= { fwRunStat 2 }
		
		-- 1.3.6.1.4.1.8596.1.2.3
		fwMIP OBJECT-TYPE
			SYNTAX DisplayString (SIZE(0..255) )
			MAX-ACCESS read-only
			STATUS current
			DESCRIPTION
				"FW Admin IP/MASK."
			::={ fwRunStat 3 }  


	END
