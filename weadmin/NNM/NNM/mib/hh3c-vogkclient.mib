-- ==========================================================================
-- Copyright (C) 2004 by H3C Technologies. All rights reserved.
--
-- Description: The purpose of this MIB file is to provide the the definition 
--              of GK(Gate Keeper) client configuration.
-- Reference:
-- ==========================================================================
HH3C-VOGKCLIENT-MIB DEFINITIONS ::= BEGIN
    IMPORTS
        OBJECT-TYPE, MODULE-IDENTITY, IpAddress, Integer32
            FROM SNMPv2-SMI
        InetAddressType, InetAddress
             FROM INET-ADDRESS-MIB
        hh3cVoice
            FROM HH3C-OID-MIB;   
    
    
            
        hh3cVoiceGKClient MODULE-IDENTITY 
            LAST-UPDATED "200503150000Z"
            ORGANIZATION
                "Hangzhou H3C Tech. Co., Ltd."
            CONTACT-INFO
                "Platform Team Hangzhou H3C Tech. Co., Ltd.
                Hai-Dian District Beijing P.R. China
                http://www.h3c.com
                Zip:100085
                "
            DESCRIPTION 
                "This MIB file is to provide the the definition of GK 
                client configuration."
            REVISION "200503150000Z"
            DESCRIPTION 
                "The initial version of this MIB file."
            ::= { hh3cVoice 8 }

--===========================================================================
--                       hh3cVoGKClientObjects
--
--===========================================================================
        hh3cVoGKClientObjects OBJECT IDENTIFIER ::= { hh3cVoiceGKClient 1 }

        
        hh3cVoRasOn OBJECT-TYPE
            SYNTAX INTEGER
                {
                enable(1),
                disable(2)
                }
            MAX-ACCESS read-write
            STATUS current
            DESCRIPTION
                "This object indicates whether the GK(Gate Keeper) client 
                function of this gateaway is enabled. 
                The value couldn't be set to enable unless hh3cVoH323GWID,
                hh3cVoGwIPAddress, hh3cVoH323GKIPAddress, and hh3cVoH323GKID 
                has been set."
            ::= { hh3cVoGKClientObjects 1 }

        
        hh3cVoGwIPAddressType OBJECT-TYPE
            SYNTAX  InetAddressType
            MAX-ACCESS read-write
            STATUS current
            DESCRIPTION
                "This object indicates the IP address type of the the interface 
                through which the gateway is connected to the GK(Gate Keeper).
                The value couldn't be modified unless hh3cVoRasOn is 'disable'."
            ::= { hh3cVoGKClientObjects 2 }
    
        
        hh3cVoGwIPAddress OBJECT-TYPE
            SYNTAX InetAddress
            MAX-ACCESS read-write
            STATUS current
            DESCRIPTION
                "This object indicates the IP address of the interface 
                through which the gateway is connected to the GK(Gate Keeper).
                The value couldn't be modified unless hh3cVoRasOn is 'disable'.
                "
            ::= { hh3cVoGKClientObjects 3 }

        
        hh3cVoH323GWID OBJECT-TYPE
            SYNTAX OCTET STRING (SIZE (0..128))
            MAX-ACCESS read-write
            STATUS current
            DESCRIPTION
                "This object indicates the ID of this H323 gateway.
                The value couldn't be modified unless hh3cVoRasOn is 
                'disable'."
            ::= { hh3cVoGKClientObjects 4 }

        
        hh3cVoH323GKID OBJECT-TYPE
            SYNTAX OCTET STRING (SIZE (0..128))
            MAX-ACCESS read-write
            STATUS current
            DESCRIPTION
                "This object indicates the ID of the GK(Gate Keeper). The value 
                couldn't be modified unless hh3cVoRasOn is 'disable'. "
            ::= { hh3cVoGKClientObjects 5 }


        hh3cVoH323GKIPAddressType OBJECT-TYPE
            SYNTAX  InetAddressType
            MAX-ACCESS read-write
            STATUS current
            DESCRIPTION
                "This object indicates the IP address of the GK(Gate Keeper). The 
                value couldn't be modified unless hh3cVoRasOn is 'disable'."
            ::= { hh3cVoGKClientObjects 6 }
    
        
        hh3cVoH323GKIPAddress OBJECT-TYPE
            SYNTAX InetAddress
            MAX-ACCESS read-write
            STATUS current
            DESCRIPTION
                "This object indicates the IP address of the GK(Gate Keeper). The 
                value couldn't be modified unless hh3cVoRasOn is 'disable'."
            ::= { hh3cVoGKClientObjects 7 }

        
        hh3cVoH323GKPort OBJECT-TYPE
            SYNTAX Integer32 (1..65535)
            MAX-ACCESS read-write
            STATUS current
            DESCRIPTION
                "This object indicates the RAS port of GK(Gate Keeper). The value 
                couldn't be modified unless hh3cVoRasOn is 'disable'."
            DEFVAL { 1719 }
            ::= { hh3cVoGKClientObjects 8 }


        hh3cVoH323GK2ID OBJECT-TYPE
            SYNTAX OCTET STRING (SIZE (0..128))
            MAX-ACCESS read-write
            STATUS current
            DESCRIPTION
                "This object indicates the ID of the slave GK(Gate Keeper).
                The value couldn't be modified unless hh3cVoRasOn is 'disable'."
            ::= { hh3cVoGKClientObjects 9 }


        hh3cVoH323GK2IPAddressType OBJECT-TYPE
            SYNTAX  InetAddressType
            MAX-ACCESS read-write
            STATUS current
            DESCRIPTION
                "This object indicates the IP address of the slave GK(Gate Keeper).
                The value couldn't be modified unless hh3cVoRasOn is 'disable'."
            ::= { hh3cVoGKClientObjects 10 }

        
        hh3cVoH323GK2IPAddress OBJECT-TYPE
            SYNTAX InetAddress
            MAX-ACCESS read-write
            STATUS current
            DESCRIPTION
                "This object indicates the IP address of the slave GK(Gate Keeper).
                The value couldn't be modified unless hh3cVoRasOn is 'disable'."
            ::= { hh3cVoGKClientObjects 11 }

        
        hh3cVoH323GK2Port OBJECT-TYPE
            SYNTAX Integer32 (1..65535)
            MAX-ACCESS read-write
            STATUS current
            DESCRIPTION
                "This object indicates the RAS communication port of slave 
                GK(Gate Keeper).
                The value couldn't be modified unless hh3cVoRasOn is 'disable'."
            DEFVAL { 1719 }
            ::= { hh3cVoGKClientObjects 12 }


        hh3cVoH323GKSecurityCall OBJECT-TYPE
            SYNTAX INTEGER
                {
                enable(1),
                disable(2)
                }
            MAX-ACCESS read-write
            STATUS current
            DESCRIPTION
                "This object indicates whether security call is enabled.
                The value couldn't be modified unless hh3cVoRasOn is 'disable'."
            ::= { hh3cVoGKClientObjects 13 }


        hh3cVoH323GKSecurityPWDType OBJECT-TYPE
            SYNTAX INTEGER
                {
                cipher(1),
                simple(2)
                }
            MAX-ACCESS read-write
            STATUS current
            DESCRIPTION
                "This object indicates the type of security call 
                password." 
            ::= { hh3cVoGKClientObjects 14 }


        hh3cVoH323GKSecurityPWD OBJECT-TYPE
            SYNTAX OCTET STRING
            MAX-ACCESS read-write
            STATUS current
            DESCRIPTION
                "This object indicates the security call password. This value 
                couldn't be modified unless hh3cVoRasOn is 'disable'."
            ::= { hh3cVoGKClientObjects 15 }

    END
