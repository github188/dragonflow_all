-- =============================================================================
-- Copyright (C) 2006 by H3C TECHNOLOGIES.  All rights reserved.
--
-- Description:
--   The file defines a MIB to provide 802.11 MAC information such
--   as station statistic and notification events.
-- Reference:
-- =============================================================================
HH3C-DOT11-STATION-MIB DEFINITIONS ::= BEGIN

IMPORTS
        MacAddress
    FROM SNMPv2-TC
        MODULE-IDENTITY,
        OBJECT-TYPE,
        NOTIFICATION-TYPE,
        Integer32,
        Unsigned32,
        Counter32,
        Counter64,
        IpAddress
    FROM SNMPv2-SMI
        hh3cDot11,
        Hh3cDot11RadioType,
        Hh3cDot11ObjectIDType,
        Hh3cDot11ChannelScopeType,
        Hh3cDot11SSIDStringType,
        Hh3cDot11AuthenType,
        Hh3cDot11AKMType,
        Hh3cDot11CipherType,
        Hh3cDot11RadioScopeType,
        Hh3cDot11SSIDEncryptModeType,
        Hh3cDot11AssocFailType,
        Hh3cDot11AuthorFailType
    FROM HH3C-DOT11-REF-MIB;

hh3cDot11STATION MODULE-IDENTITY
    LAST-UPDATED "200802251800Z"        -- Feb 25, 2008 at 18:00 GMT
    ORGANIZATION
        "Hangzhou H3C Technologies Co., Ltd."
    CONTACT-INFO
        "Platform Team Hangzhou H3C Technologies Co., Ltd.
         Hai-Dian District Beijing P.R. China
         Http://www.h3c.com
         Zip:100085"
    DESCRIPTION
        "This MIB defines the configuration and statistic information of
        stations.

        GLOSSARY

        IEEE 802.11
        Standard to encourage interoperability among
        wireless networking equipment.

        Access point (AP)
        Transmitter/receiver (transceiver) device
        that commonly connects and transports data
        between a wireless network and a wired network.

        Access control (AC)
        To control and manage multi-APs, it will bridge
        wireless and wired network.

        Control And Provisioning of Wireless Access Points Protocol
        The short name of protocol is CAPWAP. AC will control
        and manage AP by CAPWAP tunnel protocol defined by IETF.
        Also, a data tunnel will be set up between AC and AP.

        BSS
        IEEE 802.11 Basic Service Set (Radio Cell).  The
        BSS of an AP comprises of the stations directly
        associated with the AP.

        station (Client Station)
        A wireless device in a wireless network
        associated with an access point.

        MIC
        Message Integrity Check.  A MIC can, optionally,
        be added to WEP-encrypted 802.11 frames.

        SSID
        Radio Service Set ID.  It is used for identification
        during association.

        STA  (WSTA)
        A non-AP 802.11 wireless station.

        WEP
        Wired Equivalent Privacy.  'WEP' is generally used
        to refer to 802.11 encryption.

        RSSI
        It is the received signal strength indication.
        It suggests the quality of received signal.

        RTS
        Request to Send, it is used to gain control of the medium
        for the transmission of 'large' frames, in which 'large'
        is defined by the RTS threshold in the network card driver.

        CTS
        Clear to Send, it is used to answer RTS frames.

        AKM
        The authentication and key management method defined by
        802.11i, and which includes 802.1x and pre-shared key."

    REVISION "200802251800Z"        -- Feb 25, 2008 at 18:00 GMT
    DESCRIPTION
        "Modified to add new trap and add hh3cDot11StationRxNoise to hh3cDot11StationAssociateTable."
    REVISION "200712211800Z"        -- Dec 21, 2007 at 18:00 GMT
    DESCRIPTION
        "Modified to add new nodes."
    REVISION "200706212000Z"        -- Jun 21, 2007 at 20:00 GMT
    DESCRIPTION
        "Changes made for new requirements."
    REVISION "200704272000Z"        -- Apr 27, 2007 at 20:00 GMT
    DESCRIPTION
        "Modified to fix some issue."
    REVISION "200605101600Z"        -- May 10, 2006 at 19:00 GMT
    DESCRIPTION
        "The initial revision of this MIB module."
    ::= { hh3cDot11 3 }

-- *****************************************************************************
-- *  Major sections
-- *****************************************************************************
--  Station Management Group
--  DEFINED AS "The group to provide the basic information for station,
--  for example, associated station, performance data and so on."

hh3cDot11StationMtGroup OBJECT IDENTIFIER     ::= { hh3cDot11STATION 1 }
--  Station Management Group has the following children:
--  hh3cDot11StationAssociateTable            ::= { hh3cDot11APMtGroup 1 }
--  hh3cDot11StationAPRelationTable           ::= { hh3cDot11APMtGroup 2 }
--  hh3cDot11StationStatisTable               ::= { hh3cDot11APMtGroup 3 }

--  MAC Event Notification
--  DEFINED AS "The group to provide station notification information"
hh3cDot11StationNotifyGroup OBJECT IDENTIFIER ::= { hh3cDot11STATION 2 }

-- *****************************************************************************
-- *  hh3cDot11StaAssociateTable Definition
-- *****************************************************************************
hh3cDot11StationAssociateTable OBJECT-TYPE
    SYNTAX      SEQUENCE OF Hh3cDot11StationAssociateEntry
    MAX-ACCESS  not-accessible
    STATUS      current
    DESCRIPTION
        "This table contains the information of stations which are
        associating with the wireless network (current AC)."
    ::= { hh3cDot11StationMtGroup 1 }

hh3cDot11StationAssociateEntry OBJECT-TYPE
    SYNTAX      Hh3cDot11StationAssociateEntry
    MAX-ACCESS  not-accessible
    STATUS      current
    DESCRIPTION
        "Each entry contains association information of each station."
    INDEX
        {
            hh3cDot11StationMAC
        }
    ::= { hh3cDot11StationAssociateTable 1 }

Hh3cDot11StationAssociateEntry ::= SEQUENCE
    {
        hh3cDot11StationMAC                MacAddress,
        hh3cDot11StationIPAddress          IpAddress,
        hh3cDot11StationUserName           OCTET STRING,
        hh3cDot11StationTxRateSet          OCTET STRING,
        hh3cDot11StationUpTime             Unsigned32,
        hh3cDot11StationSignalStrength     Integer32,
        hh3cDot11StationRSSI               Integer32,
        hh3cDot11StationChannel            Hh3cDot11ChannelScopeType,
        hh3cDot11StationPowerSaveMode      INTEGER,
        hh3cDot11StationAid                Integer32,
        hh3cDot11StationVlanId             Integer32,
        hh3cDot11StationSSIDName           Hh3cDot11SSIDStringType,
        hh3cDot11StationAuthenMode         Hh3cDot11AuthenType,
        hh3cDot11StationAKMMode            Hh3cDot11AKMType,
        hh3cDot11StationSecurityCiphers    Hh3cDot11CipherType,
        hh3cDot11StationSSIDEncryptMode    Hh3cDot11SSIDEncryptModeType,
        hh3cDot11StationRxSNR              Integer32,
        hh3cDot11StationTxRate             Integer32,
        hh3cDot11StationRxRate             Integer32,
        hh3cDot11StationVendorName         OCTET STRING,
        hh3cDot11StationRadioMode          Hh3cDot11RadioType,
        hh3cDot11StationRxNoise            Integer32
    }

hh3cDot11StationMAC OBJECT-TYPE
    SYNTAX      MacAddress
    MAX-ACCESS  not-accessible
    STATUS      current
    DESCRIPTION
        "Represents the unique MAC Address assigned to the STA."
    ::= { hh3cDot11StationAssociateEntry 1 }

hh3cDot11StationIPAddress OBJECT-TYPE
    SYNTAX      IpAddress
    MAX-ACCESS  read-only
    STATUS      current
    DESCRIPTION
        "Represents the IP address of the station."
    ::= { hh3cDot11StationAssociateEntry 2 }

hh3cDot11StationUserName OBJECT-TYPE
    SYNTAX      OCTET STRING
    MAX-ACCESS  read-only
    STATUS      current
    DESCRIPTION
        "Represents the user name of the station."
    ::= { hh3cDot11StationAssociateEntry 3 }

hh3cDot11StationTxRateSet OBJECT-TYPE
    SYNTAX      OCTET STRING
    UNITS       "Mbps"
    MAX-ACCESS  read-only
    STATUS      current
    DESCRIPTION
        "Represents the current transmit data rates for this station.
        Each byte will represent one rate. If the MSB(Most significant bit)
        is set, then this rate is a mandantory rate. Otherwise,
        it is optional."
    ::= { hh3cDot11StationAssociateEntry 4 }

hh3cDot11StationUpTime OBJECT-TYPE
    SYNTAX      Unsigned32
    UNITS       "second"
    MAX-ACCESS  read-only
    STATUS      current
    DESCRIPTION
        "The time in seconds, how long this station has been associated
        with this device."
    ::= { hh3cDot11StationAssociateEntry 5 }

hh3cDot11StationSignalStrength OBJECT-TYPE
    SYNTAX      Integer32
    UNITS       "dBm"
    MAX-ACCESS  read-only
    STATUS      current
    DESCRIPTION
        "Represents a device-dependent measure of the signal strength
        of latest packet received from this station."
    ::= { hh3cDot11StationAssociateEntry 6 }

hh3cDot11StationRSSI OBJECT-TYPE
    SYNTAX      Integer32
    MAX-ACCESS  read-only
    STATUS      current
    DESCRIPTION
        "Represents a device-dependent measure of the RSSI.
        It is the received signal strength indication.
        The maximum value is defined by chip set vendors"
    ::= { hh3cDot11StationAssociateEntry 7 }

hh3cDot11StationChannel OBJECT-TYPE
    SYNTAX      Hh3cDot11ChannelScopeType
    MAX-ACCESS  read-only
    STATUS      current
    DESCRIPTION
        "Represents current radio channel used by station."
    ::= { hh3cDot11StationAssociateEntry 8 }

hh3cDot11StationPowerSaveMode OBJECT-TYPE
    SYNTAX      INTEGER
        {
            active(1),
            powersave(2)
        }
    MAX-ACCESS  read-only
    STATUS      current
    DESCRIPTION
        "Represents the power management mode of this station.
        The following values are supported:
        active(1)    - This station is not in power-save
        mode and it is actively sending or
        receiving data.
        powersave(2) - This station is in power-save mode and
        it wakes up after sometime to check for
        buffer data."
    DEFVAL      { active }
    ::= { hh3cDot11StationAssociateEntry 9 }

hh3cDot11StationAid OBJECT-TYPE
    SYNTAX      Integer32
    MAX-ACCESS  read-only
    STATUS      current
    DESCRIPTION
        "Represents the association identification number of stations or
        multicast addresses associating with this device."
    ::= { hh3cDot11StationAssociateEntry 10 }

hh3cDot11StationVlanId OBJECT-TYPE
    SYNTAX      Integer32
    MAX-ACCESS  read-only
    STATUS      current
    DESCRIPTION
        "Represents Vlan ID to which the station is associated."
    ::= { hh3cDot11StationAssociateEntry 11 }

hh3cDot11StationSSIDName OBJECT-TYPE
    SYNTAX      Hh3cDot11SSIDStringType
    MAX-ACCESS  read-only
    STATUS      current
    DESCRIPTION
        "Represents the ESS name."
    ::= { hh3cDot11StationAssociateEntry 12 }

hh3cDot11StationAuthenMode OBJECT-TYPE
    SYNTAX      Hh3cDot11AuthenType
    MAX-ACCESS  read-only
    STATUS      current
    DESCRIPTION
        "Represents the Authentication mode defined by 802.11."
    ::= { hh3cDot11StationAssociateEntry 13 }

hh3cDot11StationAKMMode OBJECT-TYPE
    SYNTAX      Hh3cDot11AKMType
    MAX-ACCESS  read-only
    STATUS      current
    DESCRIPTION
        "Represents the key management mode defined by 802.11i."
    ::= { hh3cDot11StationAssociateEntry 14 }

hh3cDot11StationSecurityCiphers OBJECT-TYPE
    SYNTAX      Hh3cDot11CipherType
    MAX-ACCESS  read-only
    STATUS      current
    DESCRIPTION
        "Represents the frame encryption cipher type used by
        station."
    ::= { hh3cDot11StationAssociateEntry 15 }

hh3cDot11StationSSIDEncryptMode OBJECT-TYPE
    SYNTAX      Hh3cDot11SSIDEncryptModeType
    MAX-ACCESS  read-only
    STATUS      current
    DESCRIPTION
        "Represents the encryption mode for this ESS."
    DEFVAL      { cipher }
    ::= { hh3cDot11StationAssociateEntry 16 }

hh3cDot11StationRxSNR OBJECT-TYPE
    SYNTAX      Integer32
    UNITS       "One Percent"
    MAX-ACCESS  read-only
    STATUS      current
    DESCRIPTION
        "Represents the signal and noise strength ratio of frame reception."
    ::= { hh3cDot11StationAssociateEntry 17 }

hh3cDot11StationTxRate OBJECT-TYPE
    SYNTAX      Integer32
    UNITS       "Mbps"
    MAX-ACCESS  read-only
    STATUS      current
    DESCRIPTION
        "Represents the transmission rate of frame."
    ::= { hh3cDot11StationAssociateEntry 18 }

hh3cDot11StationRxRate OBJECT-TYPE
    SYNTAX      Integer32
    UNITS       "Mbps"
    MAX-ACCESS  read-only
    STATUS      current
    DESCRIPTION
        "Represents the reception rate of frame."
    ::= { hh3cDot11StationAssociateEntry 19 }

hh3cDot11StationVendorName OBJECT-TYPE
    SYNTAX      OCTET STRING(SIZE(0..127))
    MAX-ACCESS  read-only
    STATUS      current
    DESCRIPTION
        "Represents the vendor name of the station."
    ::= { hh3cDot11StationAssociateEntry 20 }

hh3cDot11StationRadioMode OBJECT-TYPE
    SYNTAX      Hh3cDot11RadioType
    MAX-ACCESS  read-only
    STATUS      current
    DESCRIPTION
        "Represents which radio type supported by the station.
        The WLAN system support the following possible radio types.
        dot11a(1),
        dot11b(2),
        dot11g(4),
        dot11n(8)
        For a station,it could support only one radio type at
        the same time."
    ::= { hh3cDot11StationAssociateEntry 21 }

hh3cDot11StationRxNoise OBJECT-TYPE
    SYNTAX      Integer32
    MAX-ACCESS  read-only
    STATUS      current
    DESCRIPTION
        "Represents the received noise of the station."
    ::= { hh3cDot11StationAssociateEntry 22 }
-- *****************************************************************************
-- *  End of hh3cDot11StaAssociateTable Definition
-- *****************************************************************************

-- *****************************************************************************
-- *  hh3cDot11StationAPRelationTable Definition
-- *****************************************************************************
hh3cDot11StationAPRelationTable OBJECT-TYPE
    SYNTAX      SEQUENCE OF Hh3cDot11StationAPRelationEntry
    MAX-ACCESS  not-accessible
    STATUS      current
    DESCRIPTION
        "This table contains relation-ship between station, AP, Radio
        and WLANID, and the detailed information of station is kept in
        the hh3cDot11StaAssociateTable table."
    ::= { hh3cDot11StationMtGroup 2 }

hh3cDot11StationAPRelationEntry OBJECT-TYPE
    SYNTAX      Hh3cDot11StationAPRelationEntry
    MAX-ACCESS  not-accessible
    STATUS      current
    DESCRIPTION
        "Each entry contains relation-ship information
        with AP, Radio and WLANID of each station."
    INDEX
        {
            hh3cDot11StationMAC
        }
    ::= { hh3cDot11StationAPRelationTable 1 }

Hh3cDot11StationAPRelationEntry ::= SEQUENCE
    {
        hh3cDot11CurrAPID       Hh3cDot11ObjectIDType,
        hh3cDot11CurrRadioID    Hh3cDot11RadioScopeType,
        hh3cDot11CurrWlanID     Integer32
    }

hh3cDot11CurrAPID OBJECT-TYPE
    SYNTAX      Hh3cDot11ObjectIDType
    MAX-ACCESS  read-only
    STATUS      current
    DESCRIPTION
        "To uniquely identify each AP, and relation-ship
        between hh3cDot11CurrAPID and AP device will be static."
    ::= { hh3cDot11StationAPRelationEntry 1 }

hh3cDot11CurrRadioID OBJECT-TYPE
    SYNTAX      Hh3cDot11RadioScopeType
    MAX-ACCESS  read-only
    STATUS      current
    DESCRIPTION
        "Represents each radio."
    ::= { hh3cDot11StationAPRelationEntry 2 }

hh3cDot11CurrWlanID OBJECT-TYPE
    SYNTAX      Integer32
    MAX-ACCESS  read-only
    STATUS      current
    DESCRIPTION
        "Represents ID of a specific ESS."
    ::= { hh3cDot11StationAPRelationEntry 3 }
-- *****************************************************************************
-- *  End of hh3cDot11StationAPRelationTable Definition
-- *****************************************************************************

-- *****************************************************************************
-- *  hh3cDot11StationStatisTable Definition
-- *****************************************************************************
hh3cDot11StationStatisTable OBJECT-TYPE
    SYNTAX      SEQUENCE OF Hh3cDot11StationStatisEntry
    MAX-ACCESS  not-accessible
    STATUS      current
    DESCRIPTION
        "This table contains statistics and status of all
        stations in the hh3cDot11StaAssociateTable."
    ::= { hh3cDot11StationMtGroup 3 }

hh3cDot11StationStatisEntry OBJECT-TYPE
    SYNTAX      Hh3cDot11StationStatisEntry
    MAX-ACCESS  not-accessible
    STATUS      current
    DESCRIPTION
        "This entry contains statistics and status for each station."
    INDEX
        {
            hh3cDot11StationMAC
        }
    ::= { hh3cDot11StationStatisTable 1 }

Hh3cDot11StationStatisEntry ::= SEQUENCE
    {
        hh3cDot11StationRxFrameCnt        Counter32,
        hh3cDot11StationTxFrameCnt        Counter32,
        hh3cDot11StationDropFrameCnt      Counter32,
        hh3cDot11StationRxFrameBytes      Counter64,
        hh3cDot11StationTxFrameBytes      Counter64,
        hh3cDot11StationDropFrameBytes    Counter64
    }

hh3cDot11StationRxFrameCnt OBJECT-TYPE
    SYNTAX      Counter32
    MAX-ACCESS  read-only
    STATUS      current
    DESCRIPTION
        "Represents how many frames are received by station."
    ::= { hh3cDot11StationStatisEntry 1 }

hh3cDot11StationTxFrameCnt OBJECT-TYPE
    SYNTAX      Counter32
    MAX-ACCESS  read-only
    STATUS      current
    DESCRIPTION
        "Represents how many frames are sent by station."
    ::= { hh3cDot11StationStatisEntry 2 }

hh3cDot11StationDropFrameCnt OBJECT-TYPE
    SYNTAX      Counter32
    MAX-ACCESS  read-only
    STATUS      current
    DESCRIPTION
        "Represents how many frames are dropped by station."
    ::= { hh3cDot11StationStatisEntry 3 }

hh3cDot11StationRxFrameBytes OBJECT-TYPE
    SYNTAX      Counter64
    UNITS       "bytes"
    MAX-ACCESS  read-only
    STATUS      current
    DESCRIPTION
        "Represents how many bytes are received by station."
    ::= { hh3cDot11StationStatisEntry 4 }

hh3cDot11StationTxFrameBytes OBJECT-TYPE
    SYNTAX      Counter64
    UNITS       "bytes"
    MAX-ACCESS  read-only
    STATUS      current
    DESCRIPTION
        "Represents how many bytes are sent by station."
    ::= { hh3cDot11StationStatisEntry 5 }

hh3cDot11StationDropFrameBytes OBJECT-TYPE
    SYNTAX      Counter64
    UNITS       "bytes"
    MAX-ACCESS  read-only
    STATUS      current
    DESCRIPTION
        "Represents how many bytes are dropped by station."
    ::= { hh3cDot11StationStatisEntry 6 }
-- *****************************************************************************
-- *  End of hh3cDot11StationStatisTable Definition
-- *****************************************************************************

-- *****************************************************************************
-- *     Notifications OF hh3cDot11StationNotifyGroup
-- *****************************************************************************
-- 802.11 MAC Notification

hh3cDot11StationTraps OBJECT IDENTIFIER    ::= { hh3cDot11StationNotifyGroup 0 }

hh3cDot11StationMICErrorTrap NOTIFICATION-TYPE
    OBJECTS
        {
            hh3cDot11CurrAPID,
            hh3cDot11CurrRadioID,
            hh3cDot11StationTrapBSSID,
            hh3cDot11StationSSIDName,
            hh3cDot11StationTrapStaMAC
        }
    STATUS      current
    DESCRIPTION
        "This notification is to indicate the occurrence of a MIC
        failure in a certain station."
    ::= { hh3cDot11StationTraps 1 }

hh3cDot11StationAuthenErrorTrap NOTIFICATION-TYPE
    OBJECTS
        {
            hh3cDot11CurrAPID,
            hh3cDot11CurrRadioID,
            hh3cDot11StationTrapBSSID,
            hh3cDot11StationSSIDName,
            hh3cDot11StationTrapStaMAC,
            hh3cDot11StationAuthenMode,
            hh3cDot11StationAKMMode
        }
    STATUS      current
    DESCRIPTION
        "This notification is to indicate which station happened
        authentication failure."
    ::= { hh3cDot11StationTraps 2 }

hh3cDot11StationAuthorFailTrap NOTIFICATION-TYPE
    OBJECTS
        {
            hh3cDot11StationUserName,
            hh3cDot11StationTrapStaMAC,
            hh3cDot11CurrRadioID,
            hh3cDot11StationSSIDName,
            hh3cDot11StationAuthorFailCause,
            hh3cDot11StationFailCauseDesc
        }
    STATUS      current
    DESCRIPTION
        "This trap is sent if a station authorization fails."
    ::= { hh3cDot11StationTraps 3 }

hh3cDot11StationAssocFailTrap NOTIFICATION-TYPE
    OBJECTS
        {
            hh3cDot11StationTrapStaMAC,
            hh3cDot11CurrRadioID,
            hh3cDot11StationSSIDName,
            hh3cDot11StationAssocFailCause,
            hh3cDot11StationFailCauseDesc
        }
    STATUS      current
    DESCRIPTION
        "This trap is sent if a station association fails."
    ::= { hh3cDot11StationTraps 4 }

hh3cDot11StationDeAssocTrap NOTIFICATION-TYPE
    OBJECTS
        {
            hh3cDot11StationUserName,
            hh3cDot11StationTrapStaMAC,
            hh3cDot11StationVlanId,
            hh3cDot11CurrRadioID,
            hh3cDot11StationSSIDName,
            hh3cDot11StationSessionDuration
        }
    STATUS      current
    DESCRIPTION
        "This trap is sent if a station de-association occurred."
    ::= { hh3cDot11StationTraps 5 }

hh3cDot11StationAuthorSuccTrap NOTIFICATION-TYPE
    OBJECTS
        {
            hh3cDot11StationUserName,
            hh3cDot11StationTrapStaMAC,
            hh3cDot11StationVlanId,
            hh3cDot11StationSessionStartTime,
            hh3cDot11CurrRadioID,
            hh3cDot11StationSSIDName
        }
    STATUS      current
    DESCRIPTION
        "This trap is sent when a station is authorized successfully."
    ::= { hh3cDot11StationTraps 6 }

hh3cDot11StationRoamingTrap NOTIFICATION-TYPE
    OBJECTS
        {
            hh3cDot11CurrAPID,
            hh3cDot11StationUserName,
            hh3cDot11StationTrapStaMAC,
            hh3cDot11StationVlanId,
            hh3cDot11StationRoamingTime,
            hh3cDot11CurrRadioID,
            hh3cDot11StationSSIDName,
            hh3cDot11StationACIPAddress
        }
    STATUS      current
    DESCRIPTION
        "This trap is sent when a station roamed successfully."
    ::= { hh3cDot11StationTraps 7 }

-- 802.11 station Notify variable object

        hh3cDot11StationTrapVarObjects OBJECT IDENTIFIER
    ::= { hh3cDot11StationNotifyGroup 1 }

hh3cDot11StationTrapBSSID OBJECT-TYPE
    SYNTAX      MacAddress
    MAX-ACCESS  accessible-for-notify
    STATUS      current
    DESCRIPTION
        "Represents on which BSSID of AP the event happened."
    ::= { hh3cDot11StationTrapVarObjects 1 }

hh3cDot11StationTrapStaMAC OBJECT-TYPE
    SYNTAX      MacAddress
    MAX-ACCESS  accessible-for-notify
    STATUS      current
    DESCRIPTION
        "Represents the MAC address of station which happened message
        integrity check (MIC) errors."
    ::= { hh3cDot11StationTrapVarObjects 2 }

hh3cDot11StationSessionStartTime OBJECT-TYPE
    SYNTAX      Unsigned32
    UNITS       "second"
    MAX-ACCESS  accessible-for-notify
    STATUS      current
    DESCRIPTION
        "Represents the time at which the station connected."
    ::= { hh3cDot11StationTrapVarObjects 3 }

hh3cDot11StationAssocFailCause OBJECT-TYPE
    SYNTAX      Hh3cDot11AssocFailType
    MAX-ACCESS  accessible-for-notify
    STATUS      current
    DESCRIPTION
        "Represents the cause of the station association failure."
    ::= { hh3cDot11StationTrapVarObjects 4 }

hh3cDot11StationAuthorFailCause OBJECT-TYPE
    SYNTAX      Hh3cDot11AuthorFailType
    MAX-ACCESS  accessible-for-notify
    STATUS      current
    DESCRIPTION
        "Represents the cause of the station authorization failure."
    ::= { hh3cDot11StationTrapVarObjects 5 }

hh3cDot11StationFailCauseDesc OBJECT-TYPE
    SYNTAX      OCTET STRING(SIZE(0..255))
    MAX-ACCESS  accessible-for-notify
    STATUS      current
    DESCRIPTION
        "Represents the failure description of the station."
    ::= { hh3cDot11StationTrapVarObjects 6 }

hh3cDot11StationSessionDuration OBJECT-TYPE
    SYNTAX      Unsigned32
    UNITS       "second"
    MAX-ACCESS  accessible-for-notify
    STATUS      current
    DESCRIPTION
        "Represents the duration of the station sesssion."
    ::= { hh3cDot11StationTrapVarObjects 7 }

hh3cDot11StationRoamingTime OBJECT-TYPE
    SYNTAX      Unsigned32
    UNITS       "second"
    MAX-ACCESS  accessible-for-notify
    STATUS      current
    DESCRIPTION
        "Represents the time at which the station roamed."
    ::= { hh3cDot11StationTrapVarObjects 8 }

hh3cDot11StationACIPAddress OBJECT-TYPE
    SYNTAX      IpAddress
    MAX-ACCESS  accessible-for-notify
    STATUS      current
    DESCRIPTION
        "For roam-in station, it represents the ip address of home AC.
         For roam-out station, it represents the ip address of foreign AC."
    ::= { hh3cDot11StationTrapVarObjects 9 }
-- *****************************************************************************
-- *     End OF NotifyGroup
-- *****************************************************************************
END
