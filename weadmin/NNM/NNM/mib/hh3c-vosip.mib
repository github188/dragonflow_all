-- =========================================================================
-- Copyright (C) 2004 by H3C Technologies. All rights reserved.
--
-- Description: Implement the parameters configuration and information browser
--              of the SIP module.
-- Reference:
-- =========================================================================
HH3C-VOSIP-MIB DEFINITIONS ::= BEGIN
    IMPORTS
        OBJECT-TYPE, MODULE-IDENTITY, IpAddress
             FROM SNMPv2-SMI
        Integer32, Counter32, NOTIFICATION-TYPE
             FROM SNMPv2-SMI
        RowStatus
             FROM SNMPv2-TC
        InetAddressType, InetAddress
             FROM INET-ADDRESS-MIB
        hh3cVoice
             FROM HH3C-OID-MIB;


        hh3cVoSIP MODULE-IDENTITY
            LAST-UPDATED "200503150000Z"
            ORGANIZATION
                "Hangzhou H3C Tech. Co., Ltd."
            CONTACT-INFO
                "Platform Team Hangzhou H3C Tech. Co., Ltd.
                Hai-Dian District Beijing P.R. China
                http://www.h3c.com
                Zip:100085
                "
            DESCRIPTION
                "This MIB contains objects to manage the SIP client configuration.
                 Session Initiation Protocol (SIP) is an application layer control
                 protocol that can establish, modify, and terminate multimedia
                 sessions such as IP phone calls, multimedia distribution, and
                 multimedia conferences.
                 "
            REVISION "200503150000Z"
            DESCRIPTION
                 "The initial revision of this MIB module."
            ::= { hh3cVoice 12 }

--================================
-- Structure declaration
--================================
    SipMsgType ::= INTEGER
        {
        unknown (1),
        register(2),
        invite(3),
        ack(4),
        prack(5),
        cancel(6),
        bye(7),
        info(8)
        }


--===============================
-- Node definitions
--===============================
    hh3cSIPClientMIB OBJECT IDENTIFIER ::= { hh3cVoSIP 1 }


--===============================
-- hh3cSIPClientConfigObjects
--===============================
    hh3cSIPClientConfigObjects OBJECT IDENTIFIER ::= { hh3cSIPClientMIB 1 }


    hh3cSIPID OBJECT-TYPE
        SYNTAX OCTET STRING (SIZE (1..32))
        MAX-ACCESS read-write
        STATUS current
        DESCRIPTION
            "The unique identification of a SIP gateway.
            This value couldn't be modified unless
            hh3cSIPRegisterEnable is 'off'."
        ::= { hh3cSIPClientConfigObjects 1 }


    hh3cSIPPasswordType OBJECT-TYPE
        SYNTAX INTEGER
            {
            simple(1),
            cipher(2)
            }
        MAX-ACCESS read-write
        STATUS current
        DESCRIPTION
            "The display type of a SIP gateway password. By default,
            this object should have the value simple(1).
            This value couldn't be modified unless
            hh3cSIPRegisterEnable is 'off'."
        ::= { hh3cSIPClientConfigObjects 2 }


    hh3cSIPPassword OBJECT-TYPE
        SYNTAX OCTET STRING
        MAX-ACCESS read-write
        STATUS current
        DESCRIPTION
            "A SIP gateway password.  This value couldn't be
            modified unless hh3cSIPRegisterEnable is 'off'."
        ::= { hh3cSIPClientConfigObjects 3 }

    hh3cSIPSourceIPAddressType OBJECT-TYPE
        SYNTAX  InetAddressType
        MAX-ACCESS read-write
        STATUS current
        DESCRIPTION
            "The source IP address type of the local peer acting
            as UA (User Agent).
            This value couldn't be modified unless
            hh3cSIPRegisterEnable is 'off'."
        ::= { hh3cSIPClientConfigObjects 4 }

    hh3cSIPSourceIP OBJECT-TYPE
        SYNTAX InetAddress
        MAX-ACCESS read-write
        STATUS current
        DESCRIPTION
            "The source IP address of the local peer acting
            as UA (User Agent).
            This value couldn't be modified unless
            hh3cSIPRegisterEnable is 'off'."
        ::= { hh3cSIPClientConfigObjects 5 }

    hh3cSIPRegisterMode OBJECT-TYPE
        SYNTAX INTEGER
            {
             gatewayAll(1),
             gatewaySingle(2),
             phoneNumber(3)
            }
        MAX-ACCESS read-write
        STATUS current
        DESCRIPTION
            "The object describes the method to send the type of telephone number.
             gatewayAll       The register mode is gateway mode and the register
                              message contains all the POTS numbers.
             gatewaySingle    The register mode is gateway mode and every register
                              message contains only one POTS number.
             phoneNumber      The register mode is phone mode.

             Note: Please configure the object hh3cSIPRegisterPhoneNumber
                   after hh3cSIPRegisterMode has been set to phoneNumber.
                   This value couldn't be modified unless
                   hh3cSIPRegisterEnable is 'off'."
        ::= { hh3cSIPClientConfigObjects 6 }

    hh3cSIPRegisterPhoneNumber OBJECT-TYPE
        SYNTAX OCTET STRING
        MAX-ACCESS read-write
        STATUS current
        DESCRIPTION
            "The object describes the telephone number which is going to be 
            registered.
            Note: Please set value of the object hh3cIPRegisterMode to 
                  phoneNumber before configure this node.
                  This value couldn't be modified unless
                  hh3cSIPRegisterEnable is 'off'."
       ::= { hh3cSIPClientConfigObjects 7 }

    hh3cSIPRegisterEnable OBJECT-TYPE
        SYNTAX INTEGER
            {
            on(1),
            off(2)
            }
        MAX-ACCESS read-write
        STATUS current
        DESCRIPTION
            "The object describes register enable or not, default is off.
            Only if hh3cSIPServerConfigTable is configured well, then this
            node could be set 'on(1)' successfully."
        ::= { hh3cSIPClientConfigObjects 8 }


    hh3cSIPTrapsControl OBJECT-TYPE
        SYNTAX INTEGER
            {
            enabled(1),
            disabled(2)
            }
        MAX-ACCESS read-write
        STATUS current
        DESCRIPTION
            "Indicates whether the SIP module is permitted to generate traps."
        ::= { hh3cSIPClientConfigObjects 9 }

    hh3cSIPStatisticClear OBJECT-TYPE
        SYNTAX INTEGER
            {
            clear(1)
            }
        MAX-ACCESS read-write
        STATUS current
        DESCRIPTION
            "The object is used to clear the statistic information of a SIP 
            gateway.
            Note: this object only supports set operation. "
        ::= { hh3cSIPClientConfigObjects 10 }


--=======================================
-- hh3cSIPServerConfigTable
--=======================================
    hh3cSIPServerConfigTable OBJECT-TYPE
        SYNTAX SEQUENCE OF HH3CSIPServerConfigEntry
        MAX-ACCESS not-accessible
        STATUS current
        DESCRIPTION
            "A list of the SIP server configuration entries."
        ::= { hh3cSIPClientMIB 2 }


    hh3cSIPServerConfigEntry OBJECT-TYPE
        SYNTAX HH3CSIPServerConfigEntry
        MAX-ACCESS not-accessible
        STATUS current
        DESCRIPTION
            "A SIP server configuration entry contains some associated 
            information, e.g. IP address, port, etc."
        INDEX { hh3cSIPServerIPAddressType, hh3cSIPServerIPAddress, hh3cSIPServerPort}
        ::= { hh3cSIPServerConfigTable 1 }


    HH3CSIPServerConfigEntry ::=
        SEQUENCE {
            hh3cSIPServerIPAddressType
                InetAddressType,
            hh3cSIPServerIPAddress
                InetAddress,
            hh3cSIPServerPort
                Integer32,
            hh3cSIPServerType
                INTEGER,
            hh3cSIPAcceptType
                INTEGER,
            hh3cSIPServerStatus
                RowStatus
         }

    hh3cSIPServerIPAddressType OBJECT-TYPE
        SYNTAX  InetAddressType
        MAX-ACCESS accessible-for-notify
        STATUS current
        DESCRIPTION
            "The source IP address type of a SIP server."
        ::= { hh3cSIPServerConfigEntry 1 }

    hh3cSIPServerIPAddress OBJECT-TYPE
        SYNTAX InetAddress
        MAX-ACCESS accessible-for-notify
        STATUS current
        DESCRIPTION
            "The IP address of a SIP server."
        ::= { hh3cSIPServerConfigEntry 2 }

    hh3cSIPServerPort OBJECT-TYPE
        SYNTAX Integer32(1..65535)
        MAX-ACCESS accessible-for-notify
        STATUS current
        DESCRIPTION
            "The port of a SIP server."
        DEFVAL { 5060 }
        ::= { hh3cSIPServerConfigEntry 3 }


    hh3cSIPServerType OBJECT-TYPE
        SYNTAX INTEGER
            {
            master(1),
            slave(2)
            }
        MAX-ACCESS read-create
        STATUS current
        DESCRIPTION
            "The type of SIP Server."
        ::= { hh3cSIPServerConfigEntry 4 }


    hh3cSIPAcceptType OBJECT-TYPE
        SYNTAX INTEGER
            {
            inbound(1),
            all(2)
            }
        MAX-ACCESS read-create
        STATUS current
        DESCRIPTION
            "The accept type of SIP calls. By default, the object value is all(2)."
        ::= { hh3cSIPServerConfigEntry 5 }


    hh3cSIPServerStatus OBJECT-TYPE
        SYNTAX RowStatus
        MAX-ACCESS read-create
        STATUS current
        DESCRIPTION
            "This object is used to create, delete or modify a row in this table.
            To create a new row, hh3cSIPServerType must be specified.
            Note: hh3cSIPRegisterEnable must be specifed 'off' before
            modifing or destroying an existing row or creating a new row.
            "
        ::= { hh3cSIPServerConfigEntry 6 }


--=======================================
-- hh3cSIPMsgStatTable
--=======================================
    hh3cSIPMsgStatTable OBJECT-TYPE
        SYNTAX SEQUENCE OF HH3CSIPMsgStatEntry
        MAX-ACCESS not-accessible
        STATUS current
        DESCRIPTION
            "A list of SIP message statistics entries. "
        ::= { hh3cSIPClientMIB 3 }


    hh3cSIPMsgStatEntry OBJECT-TYPE
        SYNTAX HH3CSIPMsgStatEntry
        MAX-ACCESS not-accessible
        STATUS current
        DESCRIPTION
            "A collection of statistics kept for a SIP
            message. "
        INDEX { hh3cSIPMsgIndex }
        ::= { hh3cSIPMsgStatTable 1 }

    HH3CSIPMsgStatEntry ::=
        SEQUENCE {
            hh3cSIPMsgIndex
                SipMsgType,
            hh3cSIPMsgName
                OCTET STRING,    
            hh3cSIPMsgSend
                Counter32,
            hh3cSIPMsgOKSend
                Counter32,
            hh3cSIPMsgReceive
                Counter32,
            hh3cSIPMsgOKReceive
                Counter32
         }

    hh3cSIPMsgIndex OBJECT-TYPE
        SYNTAX SipMsgType
        MAX-ACCESS not-accessible
        STATUS current
        DESCRIPTION
            "The index of a SIP message."
        ::= { hh3cSIPMsgStatEntry 1 }
        
    hh3cSIPMsgName OBJECT-TYPE
        SYNTAX OCTET STRING
        MAX-ACCESS read-only
        STATUS current
        DESCRIPTION
            "The name of a SIP message."
        ::= { hh3cSIPMsgStatEntry 2 }

    hh3cSIPMsgSend OBJECT-TYPE
        SYNTAX Counter32
        MAX-ACCESS read-only
        STATUS current
        DESCRIPTION
            "The number of messages which a SIP gateway has sent."
        ::= { hh3cSIPMsgStatEntry 3 }

    hh3cSIPMsgOKSend OBJECT-TYPE
        SYNTAX Counter32
        MAX-ACCESS read-only
        STATUS current
        DESCRIPTION
            "The number of successful messages which a SIP gateway has sent."
        ::= { hh3cSIPMsgStatEntry 4 }

    hh3cSIPMsgReceive OBJECT-TYPE
        SYNTAX Counter32
        MAX-ACCESS read-only
        STATUS current
        DESCRIPTION
            "The number of messages which a SIP gateway has received."
        ::= { hh3cSIPMsgStatEntry 5 }

    hh3cSIPMsgOKReceive OBJECT-TYPE
        SYNTAX Counter32
        MAX-ACCESS read-only
        STATUS current
        DESCRIPTION
            "The number of successful messages which a SIP gateway has received."
        ::= { hh3cSIPMsgStatEntry 6 }


--=======================================
-- hh3cSIPMsgResponseStatTable
--=======================================
    hh3cSIPMsgResponseStatTable OBJECT-TYPE
        SYNTAX SEQUENCE OF HH3CSIPMsgResponseStatEntry
        MAX-ACCESS not-accessible
        STATUS current
        DESCRIPTION
            "A list of the SIP message response code statistic entries."
        ::= { hh3cSIPClientMIB 4 }


    hh3cSIPMsgResponseStatEntry OBJECT-TYPE
        SYNTAX HH3CSIPMsgResponseStatEntry
        MAX-ACCESS not-accessible
        STATUS current
        DESCRIPTION
            "The information of SIP response code."
        INDEX { hh3cSIPMsgResponseIndex }
        ::= { hh3cSIPMsgResponseStatTable 1 }

    HH3CSIPMsgResponseStatEntry ::=
        SEQUENCE {
            hh3cSIPMsgResponseIndex
                Integer32,
            hh3cSIPMsgResponseCode
                OCTET STRING,
            hh3cSIPResCodeRecvCount
                Counter32,
            hh3cSIPResCodeSendCount
                Counter32
         }

    hh3cSIPMsgResponseIndex OBJECT-TYPE
        SYNTAX Integer32
        MAX-ACCESS not-accessible
        STATUS current
        DESCRIPTION
            "The index of a SIP message response code."
        ::= { hh3cSIPMsgResponseStatEntry 1 }

    hh3cSIPMsgResponseCode OBJECT-TYPE
        SYNTAX OCTET STRING
        MAX-ACCESS read-only
        STATUS current
        DESCRIPTION
            "The SIP message response code."
        ::= { hh3cSIPMsgResponseStatEntry 2 }

    hh3cSIPResCodeRecvCount OBJECT-TYPE
        SYNTAX Counter32
        MAX-ACCESS read-only
        STATUS current
        DESCRIPTION
            "The number of SIP response code which a SIP gateway has received."
        ::= { hh3cSIPMsgResponseStatEntry 3 }

    hh3cSIPResCodeSendCount OBJECT-TYPE
        SYNTAX Counter32
        MAX-ACCESS read-only
        STATUS current
        DESCRIPTION
            "The number of SIP response code which a SIP gateway has sent."
        ::= { hh3cSIPMsgResponseStatEntry 4 }


--=======================================
-- hh3cSIPTrapStubObjects
--=======================================
    hh3cSIPTrapStubObjects OBJECT IDENTIFIER ::= { hh3cVoSIP 3 }


    hh3cSIPRegisterFailReason OBJECT-TYPE
        SYNTAX OCTET STRING (SIZE (0..31))
        MAX-ACCESS accessible-for-notify
        STATUS current
        DESCRIPTION
            "The object describes the reason that a SIP gateway fails to register."
        ::= { hh3cSIPTrapStubObjects 1 }


    hh3cSIPAuthenReqMethod OBJECT-TYPE
        SYNTAX SipMsgType
        MAX-ACCESS accessible-for-notify
        STATUS current
        DESCRIPTION
            "The object denotes the method of a request that fails to authenticate."
        ::= { hh3cSIPTrapStubObjects 2 }


--=======================================
-- hh3cSIPClientNotifications
--=======================================
    hh3cSIPClientNotifications OBJECT IDENTIFIER ::= { hh3cVoSIP 4 }


    hh3cSIPRegisterFailure NOTIFICATION-TYPE
        OBJECTS { hh3cSIPID, hh3cSIPServerIPAddressType, hh3cSIPServerIPAddress,
                  hh3cSIPServerPort, hh3cSIPRegisterFailReason }
        STATUS current
        DESCRIPTION
            "The trap is generated when a SIP gateway fails to register."
        ::= { hh3cSIPClientNotifications 1 }


    hh3cSIPAuthenticateFailure NOTIFICATION-TYPE
        OBJECTS { hh3cSIPID, hh3cSIPAuthenReqMethod }
        STATUS current
        DESCRIPTION
            "The trap is generated when a request with its credential fail to 
            authenticate."
        ::= { hh3cSIPClientNotifications 2 }


    hh3cSIPServerSwitch NOTIFICATION-TYPE
        STATUS current
        DESCRIPTION
            "The trap is generated when a switch happens between master and 
            slave SIP server."
        ::= { hh3cSIPClientNotifications 3 }

END
