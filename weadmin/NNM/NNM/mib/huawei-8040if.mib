-- =========================================================================
-- Copyright (C) 2001,2002 by  HUAWEI TECHNOLOGIES. All rights reserved.
--
-- Description: This file describes the huawei mib implementation of router interface
-- Reference:Huawei enterprise MIB
-- =========================================================================

	HUAWEI-8040IF-MIB DEFINITIONS ::= BEGIN
 
		IMPORTS
			mlsr
				FROM HUAWEI-3COM-OID-MIB			
			ifIndex			
				FROM RFC1213-MIB			
			OBJECT-GROUP, MODULE-COMPLIANCE			
				FROM SNMPv2-CONF			
			OBJECT-TYPE, MODULE-IDENTITY, Integer32
				FROM SNMPv2-SMI			
			DisplayString			
				FROM SNMPv2-TC;

	hw8040If MODULE-IDENTITY 
			LAST-UPDATED "200410110000Z"		
			ORGANIZATION 
				"Huawei-3com Technologies co.,Ltd."
			CONTACT-INFO 
				"Platform Team Beijing Institute Huawei-3com Tech, Inc.
				Http://www.huawei-3com.com                                       
				E-mail:support@huawei-3com.com "
			DESCRIPTION 
				" "
			::= { mlsr 7 }	
--
-- Node definitions
--

		hw8040IfTable OBJECT-TYPE
			SYNTAX SEQUENCE OF Hw8040IfEntry
			MAX-ACCESS not-accessible
			STATUS current
			DESCRIPTION
				"The table describles the private attributes of Quidway router.
				"
			::= { hw8040If 1 }

		
		hw8040IfEntry OBJECT-TYPE
			SYNTAX Hw8040IfEntry
			MAX-ACCESS not-accessible
			STATUS current
			DESCRIPTION
				"Each entry contains the attributes 
				associated with a Quidway router entity."
			INDEX { ifIndex }
			::= { hw8040IfTable 1 }

		
		Hw8040IfEntry ::=
			SEQUENCE { 
				hw8040IfInPerSecBits
					Integer32,
				hw8040IfOutPerSecBits
					Integer32,
				hw8040CRCIfInputErr
					Integer32,
				hw8040IfOutCollisions
					Integer32,
				hw8040IfDescCfg
					DisplayString
			 }

-- Begin definition of hw8040IfInPerSecBits object
-- ==========================================
-- The 5 minutes exponentially-decayed moving
-- average  of bits per second input from the
-- interface . 
-- ==========================================
		hw8040IfInPerSecBits OBJECT-TYPE
			SYNTAX Integer32
			MAX-ACCESS read-only
			STATUS current
			DESCRIPTION
				"
				The 5 minutes exponentially-decayed moving
				average  of bits per second input from the
				interface . 
				
				"
			::= { hw8040IfEntry 1 }

		
-- Begin definition of hw8040IfOutPerSecBits object
-- ==========================================
-- The 5 minutes exponentially-decayed moving
-- average  of bits per second input from the
-- interface . 
-- ==========================================
		hw8040IfOutPerSecBits OBJECT-TYPE
			SYNTAX Integer32
			MAX-ACCESS read-only
			STATUS current
			DESCRIPTION
				"
				The 5 minutes exponentially-decayed moving
				average  of bits per second output from the
				interface . 
				"
			::= { hw8040IfEntry 2 }

		
-- Begin definition of hw8040CRCIfInputErr object
-- CRC errors numbers of input packets .
		hw8040CRCIfInputErr OBJECT-TYPE
			SYNTAX Integer32
			MAX-ACCESS read-only
			STATUS current
			DESCRIPTION
				"
				The statistics of CRC errors of input packets
				of the interface."
			::= { hw8040IfEntry 3 }

		
-- Begin definition of hw8040IfOutCollisions object
-- The total number of output collisions detected on
-- this interface.
		hw8040IfOutCollisions OBJECT-TYPE
			SYNTAX Integer32
			MAX-ACCESS read-only
			STATUS current
			DESCRIPTION
				"
				The statistics of collision numbers of output
				which are detected on the interface."
			::= { hw8040IfEntry 4 }

		
-- Begin definition of hw8040IfDescCfg object
-- The description of the interface  which is user configurable .
		hw8040IfDescCfg OBJECT-TYPE
			SYNTAX DisplayString (SIZE (0..80))
			MAX-ACCESS read-write
			STATUS current
			DESCRIPTION
				"The description of the interface  which is user configurable ."
			::= { hw8040IfEntry 5 }

		
		
		
	
	END
