-- ==========================================================================
-- Copyright (C) 2002 by  HUAWEI TECHNOLOGIES. All rights reserved.
--
-- Description: The purpose of this MIB file is to provide the define of
--              GK client MIB of HUAWEI quidway serial router, which saves  
--              gateway config information related with its GKClient function.
-- Reference:
-- ==========================================================================
HUAWEI-VO-GK-CLIENT-MIB DEFINITIONS ::= BEGIN

	IMPORTS
		OBJECT-TYPE, MODULE-IDENTITY, IpAddress
			FROM SNMPv2-SMI
		voice
			FROM HUAWEI-3COM-OID-MIB;	
	
	
--
-- Node definitions
--
			
		hwVoiceGKClientMIB MODULE-IDENTITY 
			LAST-UPDATED "200410200000Z"		-- Oct 20, 2004  GMT
			ORGANIZATION 
				"Huawei-3COM Technologies Co., Ltd."
			CONTACT-INFO 
				"PLAT Team Huawei 3Com Technologies co.,Ltd.								
				Shang-Di Information Industry Base,
				Hai-Dian District Beijing P.R. China
				http://www.huawei-3com.com
				Zip:100085"
			DESCRIPTION 
				" "
			REVISION "200404081345Z"		-- April 08, 2004 at 13:45 GMT
			DESCRIPTION 
				""
			::= { voice 8 }

		
		hwVoGKClientObjects OBJECT IDENTIFIER ::= { hwVoiceGKClientMIB 1 }

		
--  GKClient Group
-- 
-- The objects in this group store gateway config information related 
--  with GKClient function.
		hwVoRasOn OBJECT-TYPE
			SYNTAX INTEGER
				{
				enable(1),
				disable(2)
				}
			MAX-ACCESS read-write
			STATUS current
			DESCRIPTION
				"This object expresses whether or not the GKClient function 
				of this gateaway is enabled .Before hwVoGwIPAddress
				and hwVoH323GKID being set ,this object can not be set to 
				enable."
			DEFVAL { disable }
			::= { hwVoGKClientObjects 1 }

		
		hwVoH323InterfaceIndex OBJECT-TYPE
			SYNTAX INTEGER
			MAX-ACCESS read-write
			STATUS obsolete
			DESCRIPTION
				"The index of the interface through which the gateway is 
				connected to the GateKeeper."
			::= { hwVoGKClientObjects 2 }

		
		hwVoGwIPAddress OBJECT-TYPE
			SYNTAX IpAddress
			MAX-ACCESS read-write
			STATUS current
			DESCRIPTION
				"This object expresses the IP address of the interface 
				through which the gateway is connected to the GateKeeper."
			::= { hwVoGKClientObjects 3 }

		
		hwVoH323GWID OBJECT-TYPE
			SYNTAX OCTET STRING (SIZE (0..128))
			MAX-ACCESS read-write
			STATUS current
			DESCRIPTION
				"This object expresses the ID of this H323 gateway ."
			::= { hwVoGKClientObjects 4 }

		
		hwVoH323GWSupportMode OBJECT-TYPE
			SYNTAX INTEGER
				{
				nonstandard-compatible(1),
				huawei(2)
				}
			MAX-ACCESS read-write
			STATUS obsolete
			DESCRIPTION
				"This object expresses the type of GateKeeper to which 
				this H323 gateway is connected ."
			DEFVAL { nonstandard-compatible }
			::= { hwVoGKClientObjects 5 }

		
		hwVoH323GWAreaID OBJECT-TYPE
			SYNTAX OCTET STRING (SIZE (0..960))
			MAX-ACCESS read-write
			STATUS current
			DESCRIPTION
				"This object expresses the technology prefixs of this gateway so 
				that the GateKeeper can validation the type of gateway .There are 
				thirty prefixs which can be configed in one gateway.In this object
				every prefix is seperated by a ';'.As a single prefix , only 
				character from '0' to '9' and '#' can present,its length is limited 
				to 31."
			::= { hwVoGKClientObjects 6 }

		
		hwVoH323GKID OBJECT-TYPE
			SYNTAX OCTET STRING (SIZE (0..128))
			MAX-ACCESS read-write
			STATUS current
			DESCRIPTION
				"This object expresses the ID of the GateKeeper ."
			::= { hwVoGKClientObjects 7 }

		
		hwVoH323GKIPAddress OBJECT-TYPE
			SYNTAX IpAddress
			MAX-ACCESS read-write
			STATUS current
			DESCRIPTION
				"This object expresses the IP address of the GateKeeper ."
			::= { hwVoGKClientObjects 8 }

		
		hwVoH323GKPort OBJECT-TYPE
			SYNTAX INTEGER (1..65535)
			MAX-ACCESS read-write
			STATUS current
			DESCRIPTION
				"This object expresses the RAS communication port of GateKeeper."
			::= { hwVoGKClientObjects 9 }

		hwVoH323GK2ID OBJECT-TYPE
			SYNTAX OCTET STRING (SIZE (0..128))
			MAX-ACCESS read-write
			STATUS current
			DESCRIPTION
				"This object expresses the ID of the Slave GateKeeper ."
			::= { hwVoGKClientObjects 10 }

		
		hwVoH323GK2IPAddress OBJECT-TYPE
			SYNTAX IpAddress
			MAX-ACCESS read-write
			STATUS current
			DESCRIPTION
				"This object expresses the IP address of the Slave GateKeeper ."
			::= { hwVoGKClientObjects 11 }

		
		hwVoH323GK2Port OBJECT-TYPE
			SYNTAX INTEGER (1..65535)
			MAX-ACCESS read-write
			STATUS current
			DESCRIPTION
				"This object expresses the RAS communication port of Slave GateKeeper."
			::= { hwVoGKClientObjects 12 }

		hwVoH323GKSecurityCall OBJECT-TYPE
			SYNTAX INTEGER
				{
				enable(1),
				disable(2)
				}
			MAX-ACCESS read-write
			STATUS current
			DESCRIPTION
				"enable/disable  call level security capacity"
			DEFVAL { enable }
			::= { hwVoGKClientObjects 13 }

		hwVoH323GKSecurityPWDType OBJECT-TYPE
			SYNTAX INTEGER
				{
				cipher(1),
				simple(2)
				}
			MAX-ACCESS read-write
			STATUS current
			DESCRIPTION
				" Specify registration level security Type
				    cipher    Hide the password when showing
                    simple    Don't hide the password when showing                                
                "
			DEFVAL { simple }
			::= { hwVoGKClientObjects 14 }

		hwVoH323GKSecurityPWD OBJECT-TYPE
			SYNTAX OCTET STRING (SIZE (0..24))
			MAX-ACCESS read-write
			STATUS current
			DESCRIPTION
				" register password.
				length 0 :   clear password;disable GKSecurity Capacity.
				length 1-16: set password with no encrypted  text.
				length 24:   set password with encrypted  text.
				"
			::= { hwVoGKClientObjects 15 }

		
	
	END
