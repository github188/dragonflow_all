-- =============================================================
-- Copyright (C) 2007 by H3C TECHNOLOGIES. All rights reserved.
--
-- Description: E1T1VI MIB
-- Reference: None
-- =============================================================
H3C-E1T1VI-MIB DEFINITIONS ::= BEGIN
    IMPORTS
        MODULE-IDENTITY, OBJECT-TYPE, Integer32
            FROM SNMPv2-SMI
        ifIndex
            FROM RFC1213-MIB
        h3cCommon
            FROM HUAWEI-3COM-OID-MIB;


-- =============================================================
-- E1T1VI Module
-- =============================================================
h3cE1T1VI MODULE-IDENTITY
    LAST-UPDATED    "200704051542Z"         -- Apr. 5, 2007 at 00:00 GMT
    ORGANIZATION
        "H3C Technologies Co., Ltd."
    CONTACT-INFO
        "Platform Team H3C Technologies Co., Ltd.
         Hai-Dian District Beijing P.R. China
         Http://www.h3c.com
         Zip:100085"
    DESCRIPTION
        "This MIB provides E1/T1 voice interface information that are
        excluded by RFC 1213 and RFC 2233"
    REVISION        "200704051542Z"
    DESCRIPTION
        "Initial version of this MIB module."
    ::= { h3cCommon 76 }


h3cE1T1VITable OBJECT-TYPE
    SYNTAX      SEQUENCE OF H3cE1T1VIEntry
    MAX-ACCESS  not-accessible
    STATUS      current
    DESCRIPTION
        "This table contains E1/T1 voice interface information, 
        such as the total number of using time slot."
    ::= { h3cE1T1VI 1 }

h3cE1T1VIEntry OBJECT-TYPE
    SYNTAX      H3cE1T1VIEntry
    MAX-ACCESS  not-accessible
    STATUS      current
    DESCRIPTION
        "This entry contains E1/T1 voice interface information.
        The index of this Entry is ifIndex defined in ifTable
        of RFC1213-MIB."
    INDEX
        {
            ifIndex
        }
    ::= { h3cE1T1VITable 1 }

H3cE1T1VIEntry ::= SEQUENCE
    {
        h3cE1T1VIUsingTimeslots    Integer32
    }

h3cE1T1VIUsingTimeslots OBJECT-TYPE
    SYNTAX      Integer32
    MAX-ACCESS  read-only
    STATUS      current
    DESCRIPTION
        "The total number of using time slot on this interface."
    ::= { h3cE1T1VIEntry 1 }

END
