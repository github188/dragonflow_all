-- ************************************************************************
-- Copyright (C) 2007 by H3C TECHNOLOGIES. All rights reserved.
--
-- Description: WAPI extension mib
-- Reference:
-- ************************************************************************
HH3C-WAPI-MIB DEFINITIONS ::= BEGIN

    IMPORTS
        Counter32, Unsigned32, MODULE-IDENTITY, OBJECT-TYPE
            FROM SNMPv2-SMI
        TruthValue
            FROM SNMPv2-TC
        InetAddressType, InetAddress
            FROM INET-ADDRESS-MIB
        hh3cCommon
            FROM HH3C-OID-MIB;

    hh3cwapiMIB MODULE-IDENTITY
        LAST-UPDATED "200705251757Z"
        ORGANIZATION
            "Hangzhou H3C Tech. Co., Ltd."
        CONTACT-INFO
            "Platform Team Hangzhou H3C Tech. Co., Ltd.
            Hai-Dian District Beijing P.R. China
            http://www.h3c.com
            Zip:100085
            "
        DESCRIPTION
            "H3C-WAPI-MIB is an extension of MIB in WAPI
            protocol. This MIB contains objects to
 	          manage configuration and monitor running state
 	          for WAPI feature."
        ::= { hh3cCommon 77 }

    hh3cwapiMIBObjects OBJECT IDENTIFIER ::= { hh3cwapiMIB 1 }
    hh3cwapiMIBStatsObjects OBJECT IDENTIFIER ::= { hh3cwapiMIB 2 }

--*************************************************************************
-- * hh3cwapiModeEnabled OBJECT
--*************************************************************************
    hh3cwapiModeEnabled OBJECT-TYPE
        SYNTAX TruthValue
        MAX-ACCESS read-write
        STATUS current
        DESCRIPTION
            "When this object is set to TRUE, it shall indicate that WAPI
            is enabled. Otherwise, it shall indicate that WAPI is disabled."
        ::= { hh3cwapiMIBObjects 1 }

--*************************************************************************
-- * hh3cwapiASIPAddress OBJECT
--*************************************************************************
    hh3cwapiASIPAddressType OBJECT-TYPE
        SYNTAX  InetAddressType
        MAX-ACCESS read-write
        STATUS current
        DESCRIPTION
               "This object is used to set IP addresses
               type (IPv4 or IPv6) of AS."
        DEFVAL { ipv4 }
        ::= { hh3cwapiMIBObjects 2 }

    hh3cwapiASIPAddress OBJECT-TYPE
        SYNTAX InetAddress
        MAX-ACCESS read-write
        STATUS current
        DESCRIPTION
            "This object is used to set the IP address of AS."
        ::= { hh3cwapiMIBObjects 3 }

-- ************************************************************************
-- * 9 statistics OBJECTS
-- ************************************************************************
    hh3cwapiStatsWAISignatureErrors OBJECT-TYPE
        SYNTAX Counter32
        MAX-ACCESS read-only
        STATUS current
        DESCRIPTION
            "This counter increases when the received packet of
            WAI signature is wrong."
        ::= { hh3cwapiMIBStatsObjects 1 }

    hh3cwapiStatsWAIHMACErrors OBJECT-TYPE
        SYNTAX Counter32
        MAX-ACCESS read-only
        STATUS current
        DESCRIPTION
            "This counter increases when the received packet of
            WAI message authentication key checking error occurs."
        ::= { hh3cwapiMIBStatsObjects 2 }

    hh3cwapiStatsWAIAuthRsltFailures OBJECT-TYPE
        SYNTAX Counter32
        MAX-ACCESS read-only
        STATUS current
        DESCRIPTION
            "This counter increases when the WAI authentication result is
            unsuccessful."
        ::= { hh3cwapiMIBStatsObjects 3 }

    hh3cwapiStatsWAIDiscardCounters OBJECT-TYPE
        SYNTAX Counter32
        MAX-ACCESS read-only
        STATUS current
        DESCRIPTION
            "This counter increases when the received packet of WAI are
            discarded."
        ::= { hh3cwapiMIBStatsObjects 4 }

    hh3cwapiStatsWAITimeoutCounters OBJECT-TYPE
        SYNTAX Counter32
        MAX-ACCESS read-only
        STATUS current
        DESCRIPTION
            "This counter increases when the packet of WAI overtime are
            detected."
        ::= { hh3cwapiMIBStatsObjects 5 }

    hh3cwapiStatsWAIFormatErrors OBJECT-TYPE
        SYNTAX Counter32
        MAX-ACCESS read-only
        STATUS current
        DESCRIPTION
            "This counter increases when the WAI packet of WAI format
            error is detected."
        ::= { hh3cwapiMIBStatsObjects 6 }

    hh3cwapiStatsWAICtfHskFailures OBJECT-TYPE
        SYNTAX Counter32
        MAX-ACCESS read-only
        STATUS current
        DESCRIPTION
            "This counter increases when the WAI certificate authenticates
            unsuccessfully."
        ::= { hh3cwapiMIBStatsObjects 7 }

    hh3cwapiStatsWAIUniHskFailures OBJECT-TYPE
        SYNTAX Counter32
        MAX-ACCESS read-only
        STATUS current
        DESCRIPTION
            "This counter increases when the WAI unicast cipher key
            negotiates unsuccessfully."
        ::= { hh3cwapiMIBStatsObjects 8 }

    hh3cwapiStatsWAIMulHskFailures OBJECT-TYPE
        SYNTAX Counter32
        MAX-ACCESS read-only
        STATUS current
        DESCRIPTION
            "This counter increases when the WAI multicast cipher key
            announces unsuccessfully."
        ::= { hh3cwapiMIBStatsObjects 9 }

END
