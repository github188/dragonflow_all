-- =============================================================
-- Copyright (C) 2002 by HUAWEI-3COM TECHNOLOGIES. All rights reserved.
--
-- Description: 
-- Reference:  extension of RFC 1213 and RFC 2233
-- =============================================================
H3C-T1-MIB DEFINITIONS ::= BEGIN
 
IMPORTS
        MODULE-IDENTITY,
        OBJECT-TYPE,
        Integer32,
        Counter32
                FROM SNMPv2-SMI
        MODULE-COMPLIANCE,
        OBJECT-GROUP
                FROM SNMPv2-CONF
        ifIndex
                FROM RFC1213-MIB
        h3cCommon
                FROM HUAWEI-3COM-OID-MIB;
                

                
-- =============================================================
-- T1 Module
-- =============================================================              
h3cT1    MODULE-IDENTITY
        LAST-UPDATED    "200412011436Z"
        ORGANIZATION    "Huawei-3com Technologies co.,Ltd."
        CONTACT-INFO
            "Platform Team Beijing Institute Huawei-3com Tech, Inc.
             Http://www.huawei-3com.com                                       
             E-mail:support@huawei-3com.com "
        DESCRIPTION
             "This MIB provides T1 interface information that are 
             excluded by RFC 1213 and RFC 2233"
        REVISION        "200412011436Z"
        DESCRIPTION
                "Initial version of this MIB module."
        ::= { h3cCommon 29 }
 
 
t1InterfaceStatusTable OBJECT-TYPE
        SYNTAX      SEQUENCE OF T1InterfaceStatusEntry
        MAX-ACCESS   not-accessible
        STATUS       current
        DESCRIPTION
         "This table contains interface packet statistics  "
        ::= { h3cT1 1 }
 
t1InterfaceStatusEntry OBJECT-TYPE
        SYNTAX         T1InterfaceStatusEntry
        MAX-ACCESS     not-accessible
        STATUS         current
        DESCRIPTION
         "This  entry contains interface packet statistics.
         The index of this Entry is ifIndex defined in ifTable
         of RFC1213-MIB"
        INDEX { ifIndex }
        ::= { t1InterfaceStatusTable 1 }
 
T1InterfaceStatusEntry ::= SEQUENCE  {    
        t1InterfaceInErrs            Counter32,
        t1InterfaceInRuntsErrs	     Counter32,
        t1InterfaceInGiantsErrs	     Counter32,
        t1InterfaceInCrcErrs         Counter32,  
        t1InterfaceInAlignErrs	     Counter32,
        t1InterfaceInOverRunsErrs    Counter32,
        t1InterfaceInDribblesErrs    Counter32,
        t1InterfaceInAbortedSeqErrs  Counter32,
        t1InterfaceInNoBufferErrs    Counter32,
        t1InterfaceInFramingErrs     Counter32,
        t1InterfaceOutputErrs        Counter32,
        t1InterfaceOutUnderRunErrs   Counter32,
        t1InterfaceOutCollisonsErrs  Counter32,
        t1InterfaceOutDeferedErrs    Counter32                             
        }
        
t1InterfaceInErrs        OBJECT-TYPE
        SYNTAX          Counter32
        MAX-ACCESS      read-only
        STATUS          current
        DESCRIPTION
         "The total number of error received on this interface"
        ::= { t1InterfaceStatusEntry 1 }
 
t1InterfaceInRuntsErrs   OBJECT-TYPE
        SYNTAX          Counter32
        MAX-ACCESS      read-only
        STATUS          current
        DESCRIPTION
         "The number of Runts Error(too short packet) received on this interface"
	::= { t1InterfaceStatusEntry 2 }
 
t1InterfaceInGiantsErrs	OBJECT-TYPE
        SYNTAX          Counter32
        MAX-ACCESS      read-only
        STATUS          current
        DESCRIPTION
         "The number of Giants Error(too long packet) received on this interface"
	::= { t1InterfaceStatusEntry 3 } 
	
t1InterfaceInCrcErrs     OBJECT-TYPE
        SYNTAX          Counter32
        MAX-ACCESS      read-only
        STATUS          current
        DESCRIPTION
         "The number of CRC Error received on this interface"
	::= { t1InterfaceStatusEntry 4 }  
	
t1InterfaceInAlignErrs   OBJECT-TYPE 
        SYNTAX          Counter32
        MAX-ACCESS      read-only
        STATUS          current
        DESCRIPTION
         "The number of Align Error received on this interface"
	::= { t1InterfaceStatusEntry 5 }

t1InterfaceInOverRunsErrs OBJECT-TYPE
        SYNTAX           Counter32
        MAX-ACCESS       read-only
        STATUS          current
        DESCRIPTION
         "The number of Over Runs Error received on this interface"
	::= { t1InterfaceStatusEntry 6 }

t1InterfaceInDribblesErrs  OBJECT-TYPE
        SYNTAX            Counter32
        MAX-ACCESS  	  read-only
        STATUS            current
        DESCRIPTION
         "The number of dribble packets received"
	::= { t1InterfaceStatusEntry 7 }

t1InterfaceInAbortedSeqErrs    OBJECT-TYPE
        SYNTAX                Counter32
        MAX-ACCESS            read-only
        STATUS                current
        DESCRIPTION
         "The number of AbortedSeq Error received on this interface"
	::= { t1InterfaceStatusEntry 8 }

t1InterfaceInNoBufferErrs      OBJECT-TYPE
        SYNTAX                Counter32
        MAX-ACCESS            read-only
        STATUS                current
        DESCRIPTION
         "The number of Error (no buffer available)"
	::= { t1InterfaceStatusEntry 9 }
 
t1InterfaceInFramingErrs       OBJECT-TYPE
        SYNTAX                Counter32
        MAX-ACCESS            read-only
        STATUS                current
        DESCRIPTION
         "The number of framing Errors"
	::= { t1InterfaceStatusEntry 10 }
 
t1InterfaceOutputErrs          OBJECT-TYPE
        SYNTAX                Counter32
        MAX-ACCESS            read-only
        STATUS                current
        DESCRIPTION
         "The number of total Error transmited on this interface"
	::= { t1InterfaceStatusEntry 11 }

t1InterfaceOutUnderRunErrs     OBJECT-TYPE
        SYNTAX                Counter32
        MAX-ACCESS            read-only
        STATUS                current
        DESCRIPTION
         "The number of UnderRun Error transmited on this interface"
	::= { t1InterfaceStatusEntry 12 }

t1InterfaceOutCollisonsErrs    OBJECT-TYPE
        SYNTAX                Counter32
        MAX-ACCESS            read-only
        STATUS                current
        DESCRIPTION
         "The number of Collisions Error transmited on this interface"
	::= { t1InterfaceStatusEntry 13 }

t1InterfaceOutDeferedErrs      OBJECT-TYPE
        SYNTAX                Counter32
        MAX-ACCESS            read-only
        STATUS                current
        DESCRIPTION
         "The number of Deferred Error transmited on this interface"
	::= { t1InterfaceStatusEntry 14 }

END
