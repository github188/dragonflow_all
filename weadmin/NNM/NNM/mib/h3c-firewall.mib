-- =========================================================================
-- Copyright (C) 2008 by  H3C TECHNOLOGIES. All rights reserved.
--
-- Description: The MIB is designed to get Firewall' statistic information.
-- Reference:
-- =========================================================================
H3C-FIREWALL-MIB DEFINITIONS ::= BEGIN

IMPORTS
        h3cCommon
    FROM HUAWEI-3COM-OID-MIB
        Unsigned32, Gauge32, OBJECT-TYPE, MODULE-IDENTITY
    FROM SNMPv2-SMI;


h3cFireWall MODULE-IDENTITY
    LAST-UPDATED "200801171450Z"
    ORGANIZATION
        "Hangzhou H3C Tech. Co., Ltd."
    CONTACT-INFO
        "Platform Team Hangzhou H3C Tech. Co., Ltd.
         Hai-Dian District Beijing P.R. China
         http://www.h3c.com
         Zip:100085"
    DESCRIPTION
        "The MIB is designed to manage H3C Firewall products."
    ::= { h3cCommon 88 }


--
-- Node definitions
--

h3cFirewallobject OBJECT IDENTIFIER ::= { h3cFireWall 1 }

h3cFirewallSpecs OBJECT IDENTIFIER ::= { h3cFirewallobject 1 }

h3cFWMaxConnNum OBJECT-TYPE
    SYNTAX      Unsigned32
    MAX-ACCESS  read-only
    STATUS      current
    DESCRIPTION
        "Max connection number of system."
    ::= { h3cFirewallSpecs 1 }

h3cFirewallGlobalStats OBJECT IDENTIFIER ::= { h3cFirewallobject 2 }

h3cFWConnNumCurr OBJECT-TYPE
    SYNTAX      Gauge32
    MAX-ACCESS  read-only
    STATUS      current
    DESCRIPTION
        "The number of connections that currently exist."
    ::= { h3cFirewallGlobalStats 1 }


END
