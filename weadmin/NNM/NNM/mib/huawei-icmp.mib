-- ==================================================================
-- Copyright (C) 2002 by  HUAWEI TECHNOLOGIES. All rights reserved.
--
-- Description: This file describes the huawei mib implementation of icmp
-- Reference: 
-- ==================================================================
HUAWEI-ICMP-MIB    DEFINITIONS ::= BEGIN

IMPORTS
        OBJECT-TYPE
                FROM RFC-1212
        enterprises
                FROM RFC1155-SMI
        Counter
                FROM RFC1155-SMI
        huawei,hwLocal,hwInternetProtocol
                FROM HUAWEI-3COM-OID-MIB;

rIcmp			OBJECT IDENTIFIER ::= { hwInternetProtocol 2}

--Extension of Icmp group of RFC1213 MIBII 

icmpInBadCode		OBJECT-TYPE
	SYNTAX		Counter
	ACCESS		read-only
	STATUS		mandatory
	DESCRIPTION   "The number of ICMP messages discarde because of an invalid code."
        ::=     { rIcmp 1    }

icmpInBadLen		OBJECT-TYPE
	SYNTAX		Counter
	ACCESS		read-only
	STATUS		mandatory
	DESCRIPTION   "The number of ICMP messages discarded because of an invalid ICMP body."
        ::=     { rIcmp 2 }

icmpInChecksum	OBJECT-TYPE
	SYNTAX		Counter
	ACCESS		read-only
	STATUS		mandatory
	DESCRIPTION   "The number of ICMP messages discarded because of a bad ICMP checksum."
        ::=     { rIcmp 3 }

icmpInTooShort	OBJECT-TYPE
	SYNTAX		Counter
	ACCESS		read-only
	STATUS		mandatory
	DESCRIPTION	"The number of ICMP messages discarded because of a short ICMP header."
        ::=     { rIcmp 4  }

icmpOutOldIcmp	OBJECT-TYPE
	SYNTAX		Counter
	ACCESS		read-only
	STATUS		mandatory
	DESCRIPTION	"The number of errors discarded because datagram was an ICMP messages."
        ::=     {  rIcmp 5 }

icmpOutShort		OBJECT-TYPE
	SYNTAX		Counter
	ACCESS		read-only
	STATUS		mandatory
	DESCRIPTION	"The number of errors discarded because IP datagram was too short."
         ::=     {  rIcmp 6 }

END
