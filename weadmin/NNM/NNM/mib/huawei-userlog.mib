-- =================================================================
-- Copyright (C) 2003 by  HUAWEI TECHNOLOGIES. All rights reserved
--
-- Description:This mib file is used for management of huawei userlog
--             information.
-- Reference:
-- =================================================================
HUAWEI-USERLOG-MIB DEFINITIONS ::= BEGIN

    IMPORTS
            huawei,huaweiMgmt,huaweiDatacomm
                    FROM HUAWEI-3COM-OID-MIB
            OBJECT-GROUP, MODULE-COMPLIANCE
                    FROM SNMPv2-CONF
            IpAddress, Integer32, Counter32, OBJECT-TYPE,
            MODULE-IDENTITY
                    FROM SNMPv2-SMI;


    hwUserLogMIB MODULE-IDENTITY
            LAST-UPDATED "200304100000Z"          -- April 10, 2003 at 00:00 GMT
            ORGANIZATION
                    "Huawei Technologies co.,Ltd."
            CONTACT-INFO
                    " R&D BeiJing, Huawei Technologies co.,Ltd.
                    Huawei Bld.,NO.3 Xinxi Rd.,
                    Shang-Di Information Industry Base,
                    Hai-Dian District Beijing P.R. China
                    Zip:100085
                    Http://www.huawei.com
                    E-mail:support@huawei.com "
            DESCRIPTION
                    "The HUAWEI-USERLOG-MIB contains objects to
                    Manage configuration and Monitor running state
                    for userlog feature."
            ::= { huaweiDatacomm 18 }


    hwUserlogObjects OBJECT IDENTIFIER ::= { hwUserLogMIB 1 }


    hwUserlogNatObjects OBJECT IDENTIFIER ::= { hwUserlogObjects 1 }


    hwUserlogNatVersion OBJECT-TYPE
            SYNTAX Integer32
            MAX-ACCESS read-only
            STATUS current
            DESCRIPTION
                    "NAT LOG version. Currently only version 1 is developed."
            ::= { hwUserlogNatObjects 1 }


    hwUserlogNatSyslog OBJECT-TYPE
            SYNTAX Integer32
            MAX-ACCESS read-write
            STATUS current
            DESCRIPTION
                    "
                    NAT LOG format.
                    If 1, LOG format is sysLog.
                    If 0, LOG format is UDP packet.
                    UDP packet is the default format, and is recommended.
                    "
            ::= { hwUserlogNatObjects 2 }


    hwUserlogNatSourceIP OBJECT-TYPE
            SYNTAX IpAddress
            MAX-ACCESS read-write
            STATUS current
            DESCRIPTION
                    "The Source IP address of NAT LOG UDP packet."
            ::= { hwUserlogNatObjects 3 }


    hwUserlogNatFlowBegin OBJECT-TYPE
            SYNTAX Integer32
            MAX-ACCESS read-write
            STATUS current
            DESCRIPTION
                    "
                    Log the NAT flow when it is created.
                    If 1, this function is enabled.
                    If 0, this function is disabled.
                    This function will be used when real-time monitor required.
                    "
            ::= { hwUserlogNatObjects 4 }


    hwUserlogNatActiveTime OBJECT-TYPE
            SYNTAX Integer32
            MAX-ACCESS read-write
            STATUS current
            DESCRIPTION
                    "
                    The active time for long-time existed NAT flow.
                    Unit: minute. Range: 10 minutes ~ 120 minutes.
                    When setting it, NAT flow can be logged after an interval of
                    active time.
                    This function will be used when real-time monitor required.
                    The default value 0 means real-time monitor function is disabled.
                    "
            ::= { hwUserlogNatObjects 5 }


    hwUserlogNatSlotCfgInfoTable OBJECT-TYPE
            SYNTAX SEQUENCE OF HwUserlogNatSlotCfgInfoEntry
            MAX-ACCESS not-accessible
            STATUS current
            DESCRIPTION
                    "A table of NAT LOG configuration information for the
                    specified slot."
            ::= { hwUserlogNatObjects 6 }


    hwUserlogNatSlotCfgInfoEntry OBJECT-TYPE
            SYNTAX HwUserlogNatSlotCfgInfoEntry
            MAX-ACCESS not-accessible
            STATUS current
            DESCRIPTION
                    "NAT LOG Configuration Information Entry for a slot."
            INDEX { hwUserlogNatCfgSlotNumber }
            ::= { hwUserlogNatSlotCfgInfoTable 1 }


    HwUserlogNatSlotCfgInfoEntry ::=
            SEQUENCE {
                    hwUserlogNatCfgSlotNumber
                            Integer32,
                    hwUserlogNatEnable
                            Integer32,
                    hwUserlogNatAclNumber
                            Integer32,
                    hwUserlogNatHostAddress
                            IpAddress,
                    hwUserlogNatUdpPort
                            Integer32
             }

    hwUserlogNatCfgSlotNumber OBJECT-TYPE
            SYNTAX Integer32 (0..15)
            MAX-ACCESS read-only
            STATUS current
            DESCRIPTION
                    "Slot number. Specify which slot is configured with NAT LOG. "
            ::= { hwUserlogNatSlotCfgInfoEntry 1 }


    hwUserlogNatEnable OBJECT-TYPE
            SYNTAX Integer32
            MAX-ACCESS read-write
            STATUS current
            DESCRIPTION
                    "
                    The NAT LOG feature Enable status.
                    If 1, NAT LOG is enbled.
                    If 0, NAT LOG is disabled.
                    "
            ::= { hwUserlogNatSlotCfgInfoEntry 2 }


    hwUserlogNatAclNumber OBJECT-TYPE
            SYNTAX Integer32
            MAX-ACCESS read-write
            STATUS current
            DESCRIPTION
                    "
                    Access-list number.
                    The value 0 means no ACL is specified.
                    Only when NAT LOG is enabled, can ACL be configured.
                    Only NAT flow which match the ACL will be logged.
                    "
            ::= { hwUserlogNatSlotCfgInfoEntry 3 }


    hwUserlogNatHostAddress OBJECT-TYPE
            SYNTAX IpAddress
            MAX-ACCESS read-write
            STATUS current
            DESCRIPTION
                    "The IP address of NAT LOG server. "
            ::= { hwUserlogNatSlotCfgInfoEntry 4 }


    hwUserlogNatUdpPort OBJECT-TYPE
            SYNTAX Integer32 (0..65535)
            MAX-ACCESS read-write
            STATUS current
            DESCRIPTION
                    "The UDP Port Number of NAT LOG UDP packet."
            ::= { hwUserlogNatSlotCfgInfoEntry 5 }


    hwUserlogNatSlotRunInfoTable OBJECT-TYPE
            SYNTAX SEQUENCE OF HwUserlogNatSlotRunInfoEntry
            MAX-ACCESS not-accessible
            STATUS current
            DESCRIPTION
                    "A table of NAT LOG running information for the specified slot."
            ::= { hwUserlogNatObjects 7 }


    hwUserlogNatSlotRunInfoEntry OBJECT-TYPE
            SYNTAX HwUserlogNatSlotRunInfoEntry
            MAX-ACCESS not-accessible
            STATUS current
            DESCRIPTION
                    "NAT LOG Running Information Entry for a slot."
            INDEX { hwUserlogNatRunSlotNumber }
            ::= { hwUserlogNatSlotRunInfoTable 1 }


    HwUserlogNatSlotRunInfoEntry ::=
            SEQUENCE {
                    hwUserlogNatRunSlotNumber
                            Integer32,
                    hwUserlogNatTotalEntries
                            Counter32,
                    hwUserlogNatTotalPackets
                            Counter32,
                    hwUserlogNatFailedEntries
                            Counter32,
                    hwUserlogNatFailedPackets
                            Counter32,
                    hwUserlogNatClearRunStat
                            Integer32
             }

    hwUserlogNatRunSlotNumber OBJECT-TYPE
            SYNTAX Integer32 (0..15)
            MAX-ACCESS read-only
            STATUS current
            DESCRIPTION
                    "Slot number. Specify on which slot the NAT LOG statistics
                    displayed."
            ::= { hwUserlogNatSlotRunInfoEntry 1 }


    hwUserlogNatTotalEntries OBJECT-TYPE
            SYNTAX Counter32
            MAX-ACCESS read-only
            STATUS current
            DESCRIPTION
                    "The total number of NAT flow entries which are logged."
            ::= { hwUserlogNatSlotRunInfoEntry 2 }


    hwUserlogNatTotalPackets OBJECT-TYPE
            SYNTAX Counter32
            MAX-ACCESS read-only
            STATUS current
            DESCRIPTION
                    "The total number of NAT LOG UDP packets generated by the router."
            ::= { hwUserlogNatSlotRunInfoEntry 3 }


    hwUserlogNatFailedEntries OBJECT-TYPE
            SYNTAX Counter32
            MAX-ACCESS read-only
            STATUS current
            DESCRIPTION
                    "The total number of NAT flow entries failed in outputting."
            ::= { hwUserlogNatSlotRunInfoEntry 4 }


    hwUserlogNatFailedPackets OBJECT-TYPE
            SYNTAX Counter32
            MAX-ACCESS read-only
            STATUS current
            DESCRIPTION
                    "The total number of NAT LOG UDP packets failed in outputting."
            ::= { hwUserlogNatSlotRunInfoEntry 5 }


    hwUserlogNatClearRunStat OBJECT-TYPE
            SYNTAX Integer32
            MAX-ACCESS read-write
            STATUS current
            DESCRIPTION
                    "
                    Clear the running statistics for NAT LOG. Write-only.
                    If 1, the running statistics for NAT LOG is resetted.
                    Other value is invalid.
                    "
            ::= { hwUserlogNatSlotRunInfoEntry 6 }


    hwUserlogFlowObjects OBJECT IDENTIFIER ::= { hwUserlogObjects 2 }


    hwUserlogFlowVersion OBJECT-TYPE
            SYNTAX Integer32
            MAX-ACCESS read-only
            STATUS current
            DESCRIPTION
                    "BAS FLOW LOG version. Currently only version 1 is developed."
            ::= { hwUserlogFlowObjects 1 }


    hwUserlogFlowSyslog OBJECT-TYPE
            SYNTAX Integer32
            MAX-ACCESS read-write
            STATUS current
            DESCRIPTION
                    "
                    BAS FLOW LOG format.
                    If 1, LOG format is sysLog.
                    If 0, LOG format is UDP packet.
                    UDP packet is the default format, and is recommended.
                    "
            ::= { hwUserlogFlowObjects 2 }


    hwUserlogFlowSourceIP OBJECT-TYPE
            SYNTAX IpAddress
            MAX-ACCESS read-write
            STATUS current
            DESCRIPTION
                    "The Source IP address of BAS FLOW LOG UDP packet."
            ::= { hwUserlogFlowObjects 3 }


    hwUserlogFlowFlowBegin OBJECT-TYPE
            SYNTAX Integer32
            MAX-ACCESS read-write
            STATUS current
            DESCRIPTION
                    "
                    Log the BAS flow when it is created.
                    If 1, this function is enabled.
                    If 0, this function is disabled.
                    This function will be used when real-time monitor required.
                    "
            ::= { hwUserlogFlowObjects 4 }


    hwUserlogFlowActiveTime OBJECT-TYPE
            SYNTAX Integer32
            MAX-ACCESS read-write
            STATUS current
            DESCRIPTION
                    "
                    The active time for long-time existed BAS flow.
                    Unit: minute. Range: 10 minutes ~ 120 minutes.
                    When setting it, BAS flow can be logged after an internal of
                    active time.
                    This function will be used when real-time monitor required.
                    The default value 0 means real-time monitor function is disabled.
                    "
            ::= { hwUserlogFlowObjects 5 }


    hwUserlogFlowSlotCfgInfoTable OBJECT-TYPE
            SYNTAX SEQUENCE OF HwUserlogFlowSlotCfgInfoEntry
            MAX-ACCESS not-accessible
            STATUS current
            DESCRIPTION
                    "A table of BAS FLOW LOG configuration information for the
                    specified slot."
            ::= { hwUserlogFlowObjects 6 }


    hwUserlogFlowSlotCfgInfoEntry OBJECT-TYPE
            SYNTAX HwUserlogFlowSlotCfgInfoEntry
            MAX-ACCESS not-accessible
            STATUS current
            DESCRIPTION
                    "BAS FLOW LOG Configuration Information Entry for a slot."
            INDEX { hwUserlogFlowCfgSlotNumber }
            ::= { hwUserlogFlowSlotCfgInfoTable 1 }


    HwUserlogFlowSlotCfgInfoEntry ::=
            SEQUENCE {
                    hwUserlogFlowCfgSlotNumber
                            Integer32,
                    hwUserlogFlowEnable
                            Integer32,
                    hwUserlogFlowAclNumber
                            Integer32,
                    hwUserlogFlowHostAddress
                            IpAddress,
                    hwUserlogFlowUdpPort
                            Integer32
             }

    hwUserlogFlowCfgSlotNumber OBJECT-TYPE
            SYNTAX Integer32 (0..15)
            MAX-ACCESS read-only
            STATUS current
            DESCRIPTION
                    "Slot number. Specify which slot is configured with BAS FLOW LOG."
            ::= { hwUserlogFlowSlotCfgInfoEntry 1 }


    hwUserlogFlowEnable OBJECT-TYPE
            SYNTAX Integer32
            MAX-ACCESS read-write
            STATUS current
            DESCRIPTION
                    "
                    The BAS FLOW LOG feature Enable status.
                    If 1, BAS FLOW LOG is enbled.
                    If 0, BAS FLOW LOG is disabled.
                    "
            ::= { hwUserlogFlowSlotCfgInfoEntry 2 }


    hwUserlogFlowAclNumber OBJECT-TYPE
            SYNTAX Integer32
            MAX-ACCESS read-write
            STATUS current
            DESCRIPTION
                    "
                    Access-list number.
                    The value 0 means no ACL is specified.
                    Only when BAS FLOW LOG is enabled, can ACL be configured.
                    Only BAS flow which match the ACL will be logged.
                    "
            ::= { hwUserlogFlowSlotCfgInfoEntry 3 }


    hwUserlogFlowHostAddress OBJECT-TYPE
            SYNTAX IpAddress
            MAX-ACCESS read-write
            STATUS current
            DESCRIPTION
                    "The IP address of BAS FLOW LOG server. "
            ::= { hwUserlogFlowSlotCfgInfoEntry 4 }


    hwUserlogFlowUdpPort OBJECT-TYPE
            SYNTAX Integer32 (0..65535)
            MAX-ACCESS read-write
            STATUS current
            DESCRIPTION
                    "The UDP Port Number of BAS FLOW LOG UDP packet."
            ::= { hwUserlogFlowSlotCfgInfoEntry 5 }


    hwUserlogFlowSlotRunInfoTable OBJECT-TYPE
            SYNTAX SEQUENCE OF HwUserlogFlowSlotRunInfoEntry
            MAX-ACCESS not-accessible
            STATUS current
            DESCRIPTION
                    "A table of BAS FLOW LOG running information for the specified slot."
            ::= { hwUserlogFlowObjects 7 }


    hwUserlogFlowSlotRunInfoEntry OBJECT-TYPE
            SYNTAX HwUserlogFlowSlotRunInfoEntry
            MAX-ACCESS not-accessible
            STATUS current
            DESCRIPTION
                    "Running Information Entry for a slot."
            INDEX { hwUserlogFlowRunSlotNumber }
            ::= { hwUserlogFlowSlotRunInfoTable 1 }


    HwUserlogFlowSlotRunInfoEntry ::=
            SEQUENCE {
                    hwUserlogFlowRunSlotNumber
                            Integer32,
                    hwUserlogFlowTotalEntries
                            Counter32,
                    hwUserlogFlowTotalPackets
                            Counter32,
                    hwUserlogFlowFailedEntries
                            Counter32,
                    hwUserlogFlowFailedPackets
                            Counter32,
                    hwUserlogFlowClearRunStat
                            Integer32
             }

    hwUserlogFlowRunSlotNumber OBJECT-TYPE
            SYNTAX Integer32 (0..15)
            MAX-ACCESS read-only
            STATUS current
            DESCRIPTION
                    "Slot number. Specify on which slot the BAS FLOW LOG
                    statistics displayed."
            ::= { hwUserlogFlowSlotRunInfoEntry 1 }


    hwUserlogFlowTotalEntries OBJECT-TYPE
            SYNTAX Counter32
            MAX-ACCESS read-only
            STATUS current
            DESCRIPTION
                    "The total number of BAS FLOW Entries which are logged."
            ::= { hwUserlogFlowSlotRunInfoEntry 2 }


    hwUserlogFlowTotalPackets OBJECT-TYPE
            SYNTAX Counter32
            MAX-ACCESS read-only
            STATUS current
            DESCRIPTION
                    "The total number of FLOW LOG UDP packet generated by the router."
            ::= { hwUserlogFlowSlotRunInfoEntry 3 }


    hwUserlogFlowFailedEntries OBJECT-TYPE
            SYNTAX Counter32
            MAX-ACCESS read-only
            STATUS current
            DESCRIPTION
                    "The total number of BAS FLOW  entries failed in outputting. "
            ::= { hwUserlogFlowSlotRunInfoEntry 4 }


    hwUserlogFlowFailedPackets OBJECT-TYPE
            SYNTAX Counter32
            MAX-ACCESS read-only
            STATUS current
            DESCRIPTION
                    "The total number of BAS FLOW LOG UDP packet failed in outputting."
            ::= { hwUserlogFlowSlotRunInfoEntry 5 }


    hwUserlogFlowClearRunStat OBJECT-TYPE
            SYNTAX Integer32
            MAX-ACCESS read-write
            STATUS current
            DESCRIPTION
                    "
                    Clear the running statistics for FLOW LOG. Write-only.
                    If 1, the running statistics for FLOW LOG is resetted.
                    Other value is invalid.
                    "
            ::= { hwUserlogFlowSlotRunInfoEntry 6 }


    hwUserlogAccessObjects OBJECT IDENTIFIER ::= { hwUserlogObjects 3 }


    hwUserlogAccessVersion OBJECT-TYPE
            SYNTAX Integer32
            MAX-ACCESS read-only
            STATUS current
            DESCRIPTION
                    "BAS ACCESS LOG version. Currently only version 1 is developed."
            ::= { hwUserlogAccessObjects 1 }


    hwUserlogAccessSyslog OBJECT-TYPE
            SYNTAX Integer32
            MAX-ACCESS read-write
            STATUS current
            DESCRIPTION
                    "
                    BAS ACCESS LOG format.
                    If 1, LOG format is sysLog;
                    If 0, LOG format is UDP packet.
                    UDP packet is the default format, and is recommended.
                    "
            ::= { hwUserlogAccessObjects 2 }


    hwUserlogAccessSourceIP OBJECT-TYPE
            SYNTAX IpAddress
            MAX-ACCESS read-write
            STATUS current
            DESCRIPTION
                    "The Source IP address of BAS ACCESS LOG UDP packet."
            ::= { hwUserlogAccessObjects 3 }


    hwUserlogAccessSlotCfgInfoTable OBJECT-TYPE
            SYNTAX SEQUENCE OF HwUserlogAccessSlotCfgInfoEntry
            MAX-ACCESS not-accessible
            STATUS current
            DESCRIPTION
                    "A table of BAS ACCESS LOG configuration information for the specified slot."
            ::= { hwUserlogAccessObjects 4 }


    hwUserlogAccessSlotCfgInfoEntry OBJECT-TYPE
            SYNTAX HwUserlogAccessSlotCfgInfoEntry
            MAX-ACCESS not-accessible
            STATUS current
            DESCRIPTION
                    "BAS ACCESS LOG Configuration Information Entry for a slot."
            INDEX { hwUserlogAccessCfgSlotNumber }
            ::= { hwUserlogAccessSlotCfgInfoTable 1 }


    HwUserlogAccessSlotCfgInfoEntry ::=
            SEQUENCE {
                    hwUserlogAccessCfgSlotNumber
                            Integer32,
                    hwUserlogAccessEnable
                            Integer32,
                    hwUserlogAccessHostAddress
                            IpAddress,
                    hwUserlogAccessUdpPort
                            Integer32
             }

    hwUserlogAccessCfgSlotNumber OBJECT-TYPE
            SYNTAX Integer32 (0..15)
            MAX-ACCESS read-only
            STATUS current
            DESCRIPTION
                    "Slot number. Specify which slot is configured with BAS ACCESS LOG."
            ::= { hwUserlogAccessSlotCfgInfoEntry 1 }


    hwUserlogAccessEnable OBJECT-TYPE
            SYNTAX Integer32
            MAX-ACCESS read-write
            STATUS current
            DESCRIPTION
                    "
                    The BAS ACCESS LOG feature Enable status.
                    If 1, BAS ACCESS LOG is enbled.
                    If 0, BAS ACCESS LOG is disabled.
                    "
            ::= { hwUserlogAccessSlotCfgInfoEntry 2 }


    hwUserlogAccessHostAddress OBJECT-TYPE
            SYNTAX IpAddress
            MAX-ACCESS read-write
            STATUS current
            DESCRIPTION
                    "The IP address of BAS ACCESS LOG server."
            ::= { hwUserlogAccessSlotCfgInfoEntry 3 }


    hwUserlogAccessUdpPort OBJECT-TYPE
            SYNTAX Integer32 (0..65535)
            MAX-ACCESS read-write
            STATUS current
            DESCRIPTION
                    "The UDP Port Number of BAS ACCESS LOG UDP packet."
            ::= { hwUserlogAccessSlotCfgInfoEntry 4 }


    hwUserlogAccessSlotRunInfoTable OBJECT-TYPE
            SYNTAX SEQUENCE OF HwUserlogAccessSlotRunInfoEntry
            MAX-ACCESS not-accessible
            STATUS current
            DESCRIPTION
                    "A table of BAS ACCESS LOG running information for the specified slot."
            ::= { hwUserlogAccessObjects 5 }


    hwUserlogAccessSlotRunInfoEntry OBJECT-TYPE
            SYNTAX HwUserlogAccessSlotRunInfoEntry
            MAX-ACCESS not-accessible
            STATUS current
            DESCRIPTION
                    "Running Information Entry for a slot."
            INDEX { hwUserlogAccessRunSlotNumber }
            ::= { hwUserlogAccessSlotRunInfoTable 1 }


    HwUserlogAccessSlotRunInfoEntry ::=
            SEQUENCE {
                    hwUserlogAccessRunSlotNumber
                            Integer32,
                    hwUserlogAccessTotalEntries
                            Counter32,
                    hwUserlogAccessTotalPackets
                            Counter32,
                    hwUserlogAccessFailedEntries
                            Counter32,
                    hwUserlogAccessFailedPackets
                            Counter32,
                    hwUserlogAccessClearRunStat
                            Integer32
             }

    hwUserlogAccessRunSlotNumber OBJECT-TYPE
            SYNTAX Integer32 (0..15)
            MAX-ACCESS read-only
            STATUS current
            DESCRIPTION
                    "Slot number. Specify on which slot the BAS ACCESS LOG statistics displayed."
            ::= { hwUserlogAccessSlotRunInfoEntry 1 }


    hwUserlogAccessTotalEntries OBJECT-TYPE
            SYNTAX Counter32
            MAX-ACCESS read-only
            STATUS current
            DESCRIPTION
                    "The total number of BAS ACCESS Records which are logged."
            ::= { hwUserlogAccessSlotRunInfoEntry 2 }


    hwUserlogAccessTotalPackets OBJECT-TYPE
            SYNTAX Counter32
            MAX-ACCESS read-only
            STATUS current
            DESCRIPTION
                    "The total number of ACCESS LOG UDP packet generated by the router."
            ::= { hwUserlogAccessSlotRunInfoEntry 3 }


    hwUserlogAccessFailedEntries OBJECT-TYPE
            SYNTAX Counter32
            MAX-ACCESS read-only
            STATUS current
            DESCRIPTION
                    "The total number of BAS ACCESS entries failed in outputting."
            ::= { hwUserlogAccessSlotRunInfoEntry 4 }


    hwUserlogAccessFailedPackets OBJECT-TYPE
            SYNTAX Counter32
            MAX-ACCESS read-only
            STATUS current
            DESCRIPTION
                    "The total number of BAS ACCESS LOG UDP packet failed in outputting."
            ::= { hwUserlogAccessSlotRunInfoEntry 5 }


    hwUserlogAccessClearRunStat OBJECT-TYPE
            SYNTAX Integer32
            MAX-ACCESS read-write
            STATUS current
            DESCRIPTION
                    "
                    Clear the running statistics for ACCESS LOG. Write-only.
                    If 1, the running statistics for ACCESS LOG is resetted.
                    Other value is invalid.
                    "
            ::= { hwUserlogAccessSlotRunInfoEntry 6 }


    hwUserlogNotifications OBJECT IDENTIFIER ::= { hwUserLogMIB 2 }


    hwUserlogConformance OBJECT IDENTIFIER ::= { hwUserLogMIB 3 }


    hwUserlogCompliances OBJECT IDENTIFIER ::= { hwUserlogConformance 1 }


    hwUserlogCompliance MODULE-COMPLIANCE
            STATUS current
            DESCRIPTION
                    "The compliance statement for entities which implement the
                    Huawei Userlog mib."
            MODULE -- this module
                    MANDATORY-GROUPS { hwUserlogMandatoryGroup }
            ::= { hwUserlogCompliances 1 }


    hwUserlogGroups OBJECT IDENTIFIER ::= { hwUserlogConformance 2 }


    hwUserlogMandatoryGroup OBJECT-GROUP
            OBJECTS { hwUserlogNatEnable, hwUserlogNatHostAddress, hwUserlogNatUdpPort,
                      hwUserlogFlowEnable, hwUserlogFlowHostAddress, hwUserlogFlowUdpPort,
                      hwUserlogAccessEnable, hwUserlogAccessHostAddress, hwUserlogAccessUdpPort
                    }
            STATUS current
            DESCRIPTION
                    "A collection of objects providing mandatory Userlog information."
            ::= { hwUserlogGroups 1 }


    hwUserlogConfigGroup OBJECT-GROUP
            OBJECTS { hwUserlogNatVersion, hwUserlogNatSyslog, hwUserlogNatSourceIP,
                      hwUserlogNatFlowBegin, hwUserlogNatActiveTime, hwUserlogNatCfgSlotNumber,
                      hwUserlogNatEnable, hwUserlogNatAclNumber, hwUserlogNatHostAddress,
                      hwUserlogNatUdpPort, hwUserlogFlowVersion, hwUserlogFlowSyslog,
                      hwUserlogFlowSourceIP, hwUserlogFlowFlowBegin, hwUserlogFlowActiveTime,
                      hwUserlogFlowCfgSlotNumber, hwUserlogFlowEnable, hwUserlogFlowAclNumber,
                      hwUserlogFlowHostAddress, hwUserlogFlowUdpPort, hwUserlogAccessVersion,
                      hwUserlogAccessSyslog, hwUserlogAccessSourceIP, hwUserlogAccessCfgSlotNumber,
                      hwUserlogAccessEnable, hwUserlogAccessHostAddress, hwUserlogAccessUdpPort
                    }
            STATUS current
            DESCRIPTION
                    "All configurable parameters of Userlog feature."
            ::= { hwUserlogGroups 2 }


    hwUserlogInfoGroup OBJECT-GROUP
            OBJECTS { hwUserlogNatTotalEntries, hwUserlogNatTotalPackets,
                      hwUserlogNatFailedEntries, hwUserlogNatFailedPackets,
                      hwUserlogFlowTotalEntries, hwUserlogFlowTotalPackets,
                      hwUserlogFlowFailedEntries, hwUserlogFlowFailedPackets,
                      hwUserlogAccessTotalEntries, hwUserlogAccessTotalPackets,
                      hwUserlogAccessFailedEntries, hwUserlogAccessFailedPackets
                    }
            STATUS current
            DESCRIPTION
                    "All running information of Userlog feature."
            ::= { hwUserlogGroups 3 }

END
