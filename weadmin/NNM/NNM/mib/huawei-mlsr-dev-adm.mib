-- =========================================================================
-- Copyright (C) 2001,2002 by  HUAWEI TECHNOLOGIES. All rights reserved.
--
-- Description:This file describes the huawei mib implementation of router system,
--             include:memory,configuration,flash,loghost and so on.
-- Reference:Huawei enterprise MIB
-- =========================================================================
HUAWEI-MLSR-DEV-ADM-MIB DEFINITIONS ::= BEGIN

        IMPORTS
            OBJECT-TYPE
                FROM RFC-1212
            TimeTicks, IpAddress, Gauge
                FROM RFC1155-SMI
            DisplayString
                FROM RFC1213-MIB
            huawei,products,router,mlsr
                FROM HUAWEI-3COM-OID-MIB;
--
-- Type definitions
--

--
-- Define Type Assignments:
--
-- HwFlashStatus:The flash device's status currently.
        HwFlashStatus ::= INTEGER
            {
            busy(1),
            available(2)
            }

--
-- HwFlashEreaseStatus:erease status of flash device.
--
        HwFlashEreaseStatus ::= INTEGER
            {
            hwFlhInOperating(1),
            hwFlhOpSuccess(2),
            hwFlhOpFailure(3),
            hwFlhReadOnly(4),
            hwFlhOpenFailure(5),
            hwBufferAllocationFailure(6),
            hwNoOpAfterLastPowered(7)
            }

--
-- RowStatus:the status of a conception row.
--
        RowStatus ::= INTEGER
            {
            valid(1),
            createRequest(2),
            underCreation(3),
            invalid(4)
            }


--
-- Node definitions
--

        routerGeneral OBJECT IDENTIFIER ::= { router 1 }

        attr OBJECT IDENTIFIER ::= { routerGeneral 1 }

        basis OBJECT IDENTIFIER ::= { attr 1 }


        version OBJECT-TYPE
            SYNTAX OCTET STRING
            ACCESS read-only
            STATUS mandatory
            DESCRIPTION
                "The version of the software of system ."
            ::= { basis 1 }


        trap OBJECT IDENTIFIER ::= { attr 2 }


        log OBJECT IDENTIFIER ::= { attr 3 }


        logcontroller OBJECT-TYPE
            SYNTAX INTEGER
                {
                enable(1),
                disable(2)
                }
            ACCESS read-write
            STATUS mandatory
            DESCRIPTION
                "The label of log status that is open or close.
                enable(1) indicates to open;disable(2) indicates
                to close."
            ::= { log 1 }


        loghostTable OBJECT-TYPE
            SYNTAX SEQUENCE OF LoghostEntry
            ACCESS not-accessible
            STATUS mandatory
            DESCRIPTION
                "A list of entries of host recieving log."
            ::= { log 2 }


        loghostEntry OBJECT-TYPE
            SYNTAX LoghostEntry
            ACCESS not-accessible
            STATUS mandatory
            DESCRIPTION
                "Address and level of host receiving log "
            INDEX { loghostaddress }
            ::= { loghostTable 1 }


        LoghostEntry ::=
            SEQUENCE {
                loghostIndex
                    INTEGER,
                loghostaddress
                    IpAddress,
                loghostport
                    INTEGER,
                loghostseverity
                    INTEGER,
                loghostlanguage
                    INTEGER,
                loghostfacility
                    INTEGER,
                loghostaccess
                    INTEGER,
                loghoststatus
                    RowStatus
             }

        loghostIndex OBJECT-TYPE
            SYNTAX INTEGER
            ACCESS read-only
            STATUS mandatory
            DESCRIPTION
                "The index of host that receives logs."
            ::= { loghostEntry 1 }


        loghostaddress OBJECT-TYPE
            SYNTAX IpAddress
            ACCESS read-only
            STATUS mandatory
            DESCRIPTION
                "The address of host that receives logs."
            ::= { loghostEntry 2 }


        loghostport OBJECT-TYPE
            SYNTAX INTEGER (1..65535)
            ACCESS read-only
            STATUS mandatory
            DESCRIPTION
                "The port of host that receives logs."
            ::= { loghostEntry 3 }


        loghostseverity OBJECT-TYPE
            SYNTAX INTEGER
                {
                emerg(1),
                alert(2),
                crit(3),
                err(4),
                warning(5),
                notice(6),
                info(7),
                debug(8)
                }
            ACCESS read-write
            STATUS mandatory
            DESCRIPTION
                "The severity indicates the level of log that is sended to host ."
            ::= { loghostEntry 4 }


        loghostlanguage OBJECT-TYPE
            SYNTAX INTEGER
                {
                chinese(1),
                english(2)
                }
            ACCESS read-write
            STATUS mandatory
            DESCRIPTION
                "The log in which language is incidated by loglanguage ."
            ::= { loghostEntry 5 }


        loghostfacility OBJECT-TYPE
            SYNTAX INTEGER
                {
                kern(1),
                user(2),
                mail(3),
                daemon(4),
                auth(5),
                syslog(6),
                lpr(7),
                news(8),
                uucp(9),
                cron(10),
                authpriv(11),
                ftp(12),
                local0(17),
                local1(18),
                local2(19),
                local3(20),
                local4(21),
                local5(22),
                local6(23),
                local7(24)
                }
            ACCESS read-write
            STATUS mandatory
            DESCRIPTION
                "The log that send to host is stored in the facility indicated logfacility  ."
            ::= { loghostEntry 6 }


        loghostaccess OBJECT-TYPE
            SYNTAX INTEGER { enable(1) }
            ACCESS read-write
            STATUS mandatory
            DESCRIPTION
                "The variable is the command who perform that netmanager get the saving log information at router."
            ::= { loghostEntry 7 }


        loghoststatus OBJECT-TYPE
            SYNTAX RowStatus
            ACCESS read-write
            STATUS mandatory
            DESCRIPTION
                "The status of the entry."
            ::= { loghostEntry 8 }


        logfilterTable OBJECT-TYPE
            SYNTAX SEQUENCE OF LogfilterEntry
            ACCESS not-accessible
            STATUS mandatory
            DESCRIPTION
                "A list of entries of filter filter log."
            ::= { log 3 }


        logfilterEntry OBJECT-TYPE
            SYNTAX LogfilterEntry
            ACCESS not-accessible
            STATUS mandatory
            DESCRIPTION
                "Address and level of filter filter log "
            INDEX { logfilterIndex, logdevfacility }
            ::= { logfilterTable 1 }


        LogfilterEntry ::=
            SEQUENCE {
                logfilterIndex
                    INTEGER,
                logdevfacility
                    OCTET STRING,
                logfilterstatus
                    RowStatus
             }

        logfilterIndex OBJECT-TYPE
            SYNTAX INTEGER
            ACCESS read-only
            STATUS mandatory
            DESCRIPTION
                "The index of host that receives logs."
            ::= { logfilterEntry 1 }


        logdevfacility OBJECT-TYPE
            SYNTAX OCTET STRING (SIZE (1..20))
            ACCESS read-only
            STATUS mandatory
            DESCRIPTION
                "Filter name."
            ::= { logfilterEntry 2 }


        logfilterstatus OBJECT-TYPE
            SYNTAX RowStatus
            ACCESS read-write
            STATUS mandatory
            DESCRIPTION
                "The status of the entry."
            ::= { logfilterEntry 3 }


        vrp OBJECT IDENTIFIER ::= { attr 4 }


        module OBJECT IDENTIFIER ::= { router 2 }


        moduleTable OBJECT-TYPE
            SYNTAX SEQUENCE OF ModuleEntry
            ACCESS not-accessible
            STATUS mandatory
            DESCRIPTION
                "Possible values of indices are
                1..moduleMaxmodules"
            ::= { module 1 }


        moduleEntry OBJECT-TYPE
            SYNTAX ModuleEntry
            ACCESS not-accessible
            STATUS mandatory
            DESCRIPTION
                "Possible values of indices are
                1..stackMaxChassis, 1..chassisMaxModules
                and 1..moduleMaxmodules"
            INDEX { moduleIndex }
            ::= { moduleTable 1 }


        ModuleEntry ::=
            SEQUENCE {
                moduleIndex
                    INTEGER,
                moduleSlotNum
                    INTEGER,
                moduleType
                    INTEGER,
                moduleFirstPort
                    INTEGER,
                moduleNumberOfPorts
                    INTEGER,
                moduleVersion
                    INTEGER,
                moduleSwVersion
                    DisplayString,
                moduleHwVersion
                    DisplayString
             }

        moduleIndex OBJECT-TYPE
            SYNTAX INTEGER
            ACCESS read-only
            STATUS mandatory
            DESCRIPTION
                "Module number in the module."
            ::= { moduleEntry 1 }


        moduleSlotNum OBJECT-TYPE
            SYNTAX INTEGER
            ACCESS read-only
            STATUS mandatory
            DESCRIPTION
                "Slot number in the module."
            ::= { moduleEntry 2 }


        moduleType OBJECT-TYPE
            SYNTAX INTEGER
                {
                unavailable(1),
                as(2),
                ss(3),
                bi(4),
                e12(5),
                e14(6),
                fe1(7),
                e1(8),
                fe2(9),
                vi2(11),
                vi4(12),
                vi30(13),
                s1b(14),
                sa2(15),
                as16(16),
                new8as(17),
                lsa(18),
                fxs2(19),
                fxo2(20),
                em2(21),
                fxs4(22),
                fxo4(23),
                em4(24),
                sab(25),
                e1vi(26),
                am12(27),
                am6(28),
                ndec(29),
                newsa2(30),
                aux(31),
                console(32),
                sic-wan(33),
                sic-1fe(34),
                sic-1sa(35),
                sic-3as(36),
                sic-1e1(37),
                sic-1t1(38),
                sic-1bu(39),
                sic-2bu(40),
                sic-1bs(41),
                sic-2bs(42),
                sic-1am(43),
                sic-2am(44),
                sic-1em(45),
                sic-2em(46),
                sic-1fxs(47),
                sic-2fxs(48),
                sic-1fxo(49),
                sic-2fxo(50),
                fcm6(51),
                sa8(52),
                t11(53),
                t12(54),
                t14(55),
                t1vi(56),
                fcm4(57),
                fcm2(58),
                rtb21ce3(59),
                ame6(60),
                ame12(61),
                e11-f(65),
                e12-f(66),
                e14-f(67),
                t11-f(68),
                t12-f(69),
                t14-f(70),
                e11-f-17(71),
                t11-f-17(72),
                rtb21ct3(73),
                atmadsl1(74),
                atmadsl2(75),
                atm155m(76),
                ase8(77),
                ase16(78),
                sae4(79),
                sae2(80),
                atmshdsl1(90),
                atmshdsl2(91),
                atmshdsl4(92),
                atm25m(93),
                atme3(94),
                atmt3(95),
                xdsl-fec(96),
                xdsl-adsl(97),
                xdsl-gshdsl(98),
                xdsl-bri(99),
                xdsl-scc(100),
                ge1(101),
                pos155m(102),
                cpos(103),
                fe1op(104),
                sae8(105),
                atm155m-mm(106),
                atm155m-sm(107),
                atm155m-sml(108),
                fe1op-sfx(109),
                fe1op-mfx(110),
                cpos-t1(111),
                ge1-op(112),
                ge2-op(113),
                ge2(114),
                fix-1wan(115),
                fix-1sae(116),
                cavium(117),
                sic-1Eth(118),
                atm1ADSLI(119),
                atm2ADSLI(120),
                fix-e11(121),
                fix-t11(122),
                e18-75(123),
                e18-120(124),
                t18(125),
                sic-1vifxs(126),
                sic-1vifxo(127),
                sic-2vifxs(128),
                sic-2vifxo(129),
                xdsl-fec-new(130),
                xdsl-sa(131),
                bs4(132),
                ima-8e175(133),
                ima-8e1120(134),
                ima-4e175(135),
                ima-4e1120(136),
                ima-8t1(137),
                ima-4t1(138),
                sic-1t1f(139),
                sic-1e1f(140),
                --  the enum values from 141 to 150 are reserved.
                fe4(149),
                atm1shdsl4wire(151),
                atmIma4shdsl(152),
                ls4(153),
                ls8(154),
                ls16(155),
                sic-adls2plus-isdn(156),
                sic-adls2plus-pots(157),
                ft3(158),
                ce32(159),
                bsv2(160),
                bsv4(161),
                rpu(162),
                erpu(163),
                ssl(164),
                nsa(165),
                fe18-75(220),
                fe18-120(221),
                ft18(222),
                cf-card(223),
                bsv2-v2(224),
                e1vi1-v2(225),
                e1vi2(226),
                t1vi1-v2(227),
                t1vi2(228),
                osm(229),
                sd707(230),
                dm-epri(231),
                dm-tpri(232),
                erpu-h(233)
                }
            ACCESS read-only
            STATUS mandatory
            DESCRIPTION
                "The product identification of the  module."
            ::= { moduleEntry 3 }


        moduleFirstPort OBJECT-TYPE
            SYNTAX INTEGER
            ACCESS read-only
            STATUS mandatory
            DESCRIPTION
                "The portIndex of the first port on the module."
            ::= { moduleEntry 4 }


        moduleNumberOfPorts OBJECT-TYPE
            SYNTAX INTEGER
            ACCESS read-only
            STATUS mandatory
            DESCRIPTION
                "The number of ports on the  module."
            ::= { moduleEntry 5 }


        moduleVersion OBJECT-TYPE
            SYNTAX INTEGER
            ACCESS read-only
            STATUS obsolete
            DESCRIPTION
                "Hardware version number for this module.
                First version is 0, second is 1, and so on."
            ::= { moduleEntry 6 }

        moduleSwVersion OBJECT-TYPE
            SYNTAX DisplayString
            ACCESS read-only
            STATUS mandatory
            DESCRIPTION
                "Software version number for this module."
            ::= { moduleEntry 7 }

        moduleHwVersion OBJECT-TYPE
            SYNTAX DisplayString
            ACCESS read-only
            STATUS mandatory
            DESCRIPTION
                "Hardware version number for this module."
            ::= { moduleEntry 8 }


-- ===============================================
--  Define local huawei Flash managemet
-- ===============================================
        hwFlashMan OBJECT IDENTIFIER ::= { router 3 }


--
-- ==================================================
-- Begin define hwFlhTotalSize(huawei flash total size)
-- ==================================================
        hwFlhTotalSize OBJECT-TYPE
            SYNTAX INTEGER
            ACCESS read-only
            STATUS mandatory
            DESCRIPTION
                "Total size of the Flash device."
            ::= { hwFlashMan 1 }


--
-- ==================================================
-- Begin define hwFlhUnusedSize(huawei flash unused size)
-- ==================================================
        hwFlhUnusedSize OBJECT-TYPE
            SYNTAX INTEGER
            ACCESS read-only
            STATUS mandatory
            DESCRIPTION
                "Free space within a Flash."
            ::= { hwFlashMan 2 }


--
-- ==================================================
-- Begin define hwFlhEraseTime(huawei flash erease time)
-- ==================================================
        hwFlhEraseTime OBJECT-TYPE
            SYNTAX TimeTicks
            ACCESS read-only
            STATUS mandatory
            DESCRIPTION
                "
                The last time of the flash device ereased.
                The value of the object is the time of sysUpTime.
                "
            ::= { hwFlashMan 3 }


--
-- ==================================================
-- Begin define hwFlhEraseStat(huawei flash erase status)
-- ==================================================
        hwFlhEraseStat OBJECT-TYPE
            SYNTAX HwFlashEreaseStatus
            ACCESS read-only
            STATUS mandatory
            DESCRIPTION
                "The flash ereasing status."
            ::= { hwFlashMan 4 }


--
-- ==================================================
-- Begin define hwFlhCurStat (huawei flash current status)
-- ==================================================
        hwFlhCurStat OBJECT-TYPE
            SYNTAX HwFlashStatus
            ACCESS read-only
            STATUS mandatory
            DESCRIPTION
                "The flash's current status."
            ::= { hwFlashMan 5 }


-- The groups consist of a lot of mix infomation on a router.
        huaweiMixinfo OBJECT IDENTIFIER ::= { router 4 }


        hwModuleId OBJECT-TYPE
            SYNTAX DisplayString
            ACCESS read-only
            STATUS mandatory
            DESCRIPTION
                "Unique ID string. Defaults to module ID
                number if available, otherwise empty."
            ::= { huaweiMixinfo 1 }


-- System description and version information.
        hwROMID OBJECT-TYPE
            SYNTAX DisplayString
            ACCESS read-only
            STATUS mandatory
            DESCRIPTION
                "System description and version information."
            ::= { huaweiMixinfo 2 }


        hwROMVersion OBJECT-TYPE
            SYNTAX DisplayString
            ACCESS read-only
            STATUS mandatory
            DESCRIPTION
                "The version of systen ROM."
            ::= { huaweiMixinfo 3 }


        hwROMSysVersion OBJECT-TYPE
            SYNTAX DisplayString
            ACCESS read-only
            STATUS mandatory
            DESCRIPTION
                "The software version of system ROM"
            ::= { huaweiMixinfo 4 }


        hwRAMSize OBJECT-TYPE
            SYNTAX INTEGER
            ACCESS read-only
            STATUS mandatory
            DESCRIPTION
                "The total size of system RAM.The unit is Byte."
            ::= { huaweiMixinfo 5 }


        hwNVRAMSize OBJECT-TYPE
            SYNTAX INTEGER
            ACCESS read-only
            STATUS mandatory
            DESCRIPTION
                "
                The total size of system non-volatile memory.
                The unit is Byte.
                "
            ::= { huaweiMixinfo 6 }


        hwNVRAMUsed OBJECT-TYPE
            SYNTAX INTEGER
            ACCESS read-only
            STATUS mandatory
            DESCRIPTION
                "The usage of system non-volatile memory. The unit is Byte."
            ::= { huaweiMixinfo 7 }


        hwConfigReg OBJECT-TYPE
            SYNTAX INTEGER
                {
                flash(1),
                nvram(2)
                }
            ACCESS read-only
            STATUS mandatory
            DESCRIPTION
                "This variable indicates the system register's value."
            ::= { huaweiMixinfo 8 }


        hwConfigRegNextReboot OBJECT-TYPE
            SYNTAX INTEGER
            ACCESS read-only
            STATUS mandatory
            DESCRIPTION
                "This variable indicates the system register's value when next reboot."
            ::= { huaweiMixinfo 9 }


        hwTFTPEnabled OBJECT-TYPE
            SYNTAX INTEGER
                {
                yes(1),
                no(2)
                }
            ACCESS read-only
            STATUS mandatory
            DESCRIPTION
                "
                If yes, indicates that the device can be configed through tftp.
                If no indicates that the device cannt be configed through tftp.
                "
            ::= { huaweiMixinfo 10 }


        hwMemoryFree OBJECT-TYPE
            SYNTAX INTEGER
            ACCESS read-only
            STATUS obsolete
            DESCRIPTION
                "
                The hwMemoryFree mib object is obsolete as of
                the variable hwMemoryFree in hwMemoryTable
                "
            ::= { huaweiMixinfo 11 }


        hwCpuCostRatePer5Sec OBJECT-TYPE
            SYNTAX INTEGER
            ACCESS read-only
            STATUS mandatory
            DESCRIPTION
                "The system CPU average busy percentage in the last 5 seconds period."
            ::= { huaweiMixinfo 12 }


        hwCpuCostRatePer5Minute OBJECT-TYPE
            SYNTAX INTEGER
            ACCESS read-only
            STATUS mandatory
            DESCRIPTION
                "The system CPU average busy percentage in the last 5 minutes period."
            ::= { huaweiMixinfo 13 }


        hwCurrentTime OBJECT-TYPE
            SYNTAX TimeTicks
            ACCESS read-only
            STATUS mandatory
            DESCRIPTION
                "The current time (in timetick: hundredths of a second)"
            ::= { huaweiMixinfo 14 }


        hwSysAirFlowTempIn OBJECT-TYPE
            SYNTAX INTEGER
                {
                ok(0),
                overcold(1),
                overhot(2)
                }
            ACCESS read-only
            STATUS mandatory
            DESCRIPTION
                "The current temperature of system.If the temperature is normal,ok(0) will return;
                If too cold,overcold(1) will return;If too hot,overhot(2) will return."
            ::= { huaweiMixinfo 15 }


        hwBuzzerStatus OBJECT-TYPE
            SYNTAX INTEGER
                {
                silence(1),
                tweet(2)
                }
            ACCESS read-only
            STATUS mandatory
            DESCRIPTION
                "The current status of buzzer. silence(1)
                indicates the status is silence;tweet(2) indicates
                the status is tweet."
            ::= { huaweiMixinfo 16 }


        hwFansStatus OBJECT-TYPE
            SYNTAX INTEGER
                {
                running(0),
                stopping(1),
                nofan(2)
                }
            ACCESS read-only
            STATUS mandatory
            DESCRIPTION
                "The current status of system fan: running(0) indicates
                the fan is running;stopping(1) indicates the fan is stopping;
                nofan(2) indicates no fan in the device. "
            ::= { huaweiMixinfo 17 }


        hwPowerStatus OBJECT-TYPE
            SYNTAX INTEGER
                {
                ok(0),
                fail(1),
                nopower(2)
                }
            ACCESS read-only
            STATUS mandatory
            DESCRIPTION
                "The current status of system power: 0:ok;1:fail;2:nopower. "
            ::= { huaweiMixinfo 18 }

        hwSecondPowerStatus OBJECT-TYPE
            SYNTAX INTEGER
                {
                ok(0),
                fail(1),
                nopower(2)
                }
            ACCESS read-only
            STATUS mandatory
            DESCRIPTION
                "The current status of second system power: 0:ok;1:fail;2:nopower. "
            ::= { huaweiMixinfo 19 }



-- huawei memory management mib
        huaweiMemoryMan OBJECT IDENTIFIER ::= { router 5 }


-- Bengin define hwUsedMemory
        hwUsedMemory OBJECT-TYPE
            SYNTAX Gauge
            ACCESS read-only
            STATUS mandatory
            DESCRIPTION
                "The use size of the memory. The unit is Byte."
            ::= { huaweiMemoryMan 1 }


-- Bengin define hwFreeMemory
        hwFreeMemory OBJECT-TYPE
            SYNTAX Gauge
            ACCESS read-only
            STATUS mandatory
            DESCRIPTION
                "The free size of the memory. The unit is Byte"
            ::= { huaweiMemoryMan 2 }


-- Bengin define hwMemoryLargestFree
        hwMemoryLargestFree OBJECT-TYPE
            SYNTAX Gauge
            ACCESS read-only
            STATUS mandatory
            DESCRIPTION
                "
                The largest free size of the contiguous area in memory.
                The unit is byte.
                "
            ::= { huaweiMemoryMan 3 }


-- Bengin define buffer32Size
        hwBuffer32Size OBJECT-TYPE
            SYNTAX INTEGER
            ACCESS read-only
            STATUS mandatory
            DESCRIPTION
                "Contains the size of 32 byte buffers."
            ::= { huaweiMemoryMan 4 }


-- Bengin define buffer32Total
        hwBuffer32Total OBJECT-TYPE
            SYNTAX INTEGER
            ACCESS read-only
            STATUS mandatory
            DESCRIPTION
                "Contains the total number of 32 byte buffers."
            ::= { huaweiMemoryMan 5 }


-- Bengin define buffer32Free
        hwBuffer32Free OBJECT-TYPE
            SYNTAX INTEGER
            ACCESS read-only
            STATUS mandatory
            DESCRIPTION
                "Contains the number of free 32 byte buffers."
            ::= { huaweiMemoryMan 6 }


        hwBuffer32Used OBJECT-TYPE
            SYNTAX INTEGER
            ACCESS read-only
            STATUS mandatory
            DESCRIPTION
                "Contains the number of used 32 byte buffers."
            ::= { huaweiMemoryMan 7 }


        hwBuffer32DropCounts OBJECT-TYPE
            SYNTAX INTEGER
            ACCESS read-only
            STATUS mandatory
            DESCRIPTION
                "Contains the number of Drop 32 byte buffers."
            ::= { huaweiMemoryMan 8 }


        hwBuffer32FreeError2 OBJECT-TYPE
            SYNTAX INTEGER
            ACCESS read-only
            STATUS mandatory
            DESCRIPTION
                "Contains the number of Free Error2 32 byte buffers."
            ::= { huaweiMemoryMan 9 }


        hwBuffer32FreeError3 OBJECT-TYPE
            SYNTAX INTEGER
            ACCESS read-only
            STATUS mandatory
            DESCRIPTION
                "Contains the number of Free Error3 32 byte buffers."
            ::= { huaweiMemoryMan 10 }


        hwBuffer32CollectCounts OBJECT-TYPE
            SYNTAX INTEGER
            ACCESS read-only
            STATUS mandatory
            DESCRIPTION
                "Contains the number of Collect 32 byte buffers."
            ::= { huaweiMemoryMan 11 }


        hwBuffer64Size OBJECT-TYPE
            SYNTAX INTEGER
            ACCESS read-only
            STATUS mandatory
            DESCRIPTION
                "Contains the size of 64 byte buffers."
            ::= { huaweiMemoryMan 12 }


        hwBuffer64Total OBJECT-TYPE
            SYNTAX INTEGER
            ACCESS read-only
            STATUS mandatory
            DESCRIPTION
                "Contains the total number of 64 byte buffers."
            ::= { huaweiMemoryMan 13 }


        hwBuffer64Free OBJECT-TYPE
            SYNTAX INTEGER
            ACCESS read-only
            STATUS mandatory
            DESCRIPTION
                "Contains the number of free 64 byte buffers."
            ::= { huaweiMemoryMan 14 }


        hwBuffer64Used OBJECT-TYPE
            SYNTAX INTEGER
            ACCESS read-only
            STATUS mandatory
            DESCRIPTION
                "Contains the number of used 64 byte buffers."
            ::= { huaweiMemoryMan 15 }


        hwBuffer64DropCounts OBJECT-TYPE
            SYNTAX INTEGER
            ACCESS read-only
            STATUS mandatory
            DESCRIPTION
                "Contains the number of Drop 64 byte buffers."
            ::= { huaweiMemoryMan 16 }


        hwBuffer64FreeError2 OBJECT-TYPE
            SYNTAX INTEGER
            ACCESS read-only
            STATUS mandatory
            DESCRIPTION
                "Contains the number of Free Error2 64 byte buffers."
            ::= { huaweiMemoryMan 17 }


        hwBuffer64FreeError3 OBJECT-TYPE
            SYNTAX INTEGER
            ACCESS read-only
            STATUS mandatory
            DESCRIPTION
                "Contains the number of Free Error3 64 byte buffers."
            ::= { huaweiMemoryMan 18 }


        hwBuffer64CollectCounts OBJECT-TYPE
            SYNTAX INTEGER
            ACCESS read-only
            STATUS mandatory
            DESCRIPTION
                "Contains the number of Collect 64 byte buffers."
            ::= { huaweiMemoryMan 19 }


        hwBuffer128Size OBJECT-TYPE
            SYNTAX INTEGER
            ACCESS read-only
            STATUS mandatory
            DESCRIPTION
                "Contains the size of 128 byte buffers."
            ::= { huaweiMemoryMan 20 }


        hwBuffer128Total OBJECT-TYPE
            SYNTAX INTEGER
            ACCESS read-only
            STATUS mandatory
            DESCRIPTION
                "Contains the total number of 128 byte buffers."
            ::= { huaweiMemoryMan 21 }


        hwBuffer128Free OBJECT-TYPE
            SYNTAX INTEGER
            ACCESS read-only
            STATUS mandatory
            DESCRIPTION
                "Contains the number of free 128 byte buffers."
            ::= { huaweiMemoryMan 22 }


        hwBuffer128Used OBJECT-TYPE
            SYNTAX INTEGER
            ACCESS read-only
            STATUS mandatory
            DESCRIPTION
                "Contains the number of used 128 byte buffers."
            ::= { huaweiMemoryMan 23 }


        hwBuffer128DropCounts OBJECT-TYPE
            SYNTAX INTEGER
            ACCESS read-only
            STATUS mandatory
            DESCRIPTION
                "Contains the number of Drop 128 byte buffers."
            ::= { huaweiMemoryMan 24 }


        hwBuffer128FreeError2 OBJECT-TYPE
            SYNTAX INTEGER
            ACCESS read-only
            STATUS mandatory
            DESCRIPTION
                "Contains the number of Free Error2 128 byte buffers."
            ::= { huaweiMemoryMan 25 }


        hwBuffer128FreeError3 OBJECT-TYPE
            SYNTAX INTEGER
            ACCESS read-only
            STATUS mandatory
            DESCRIPTION
                "Contains the number of Free Error3 128 byte buffers."
            ::= { huaweiMemoryMan 26 }


        hwBuffer128CollectCounts OBJECT-TYPE
            SYNTAX INTEGER
            ACCESS read-only
            STATUS mandatory
            DESCRIPTION
                "Contains the number of Collect 128 byte buffers."
            ::= { huaweiMemoryMan 27 }


        hwBuffer256Size OBJECT-TYPE
            SYNTAX INTEGER
            ACCESS read-only
            STATUS mandatory
            DESCRIPTION
                "Contains the size of 256 byte buffers."
            ::= { huaweiMemoryMan 28 }


        hwBuffer256Total OBJECT-TYPE
            SYNTAX INTEGER
            ACCESS read-only
            STATUS mandatory
            DESCRIPTION
                "Contains the total number of 256 byte buffers."
            ::= { huaweiMemoryMan 29 }


        hwBuffer256Free OBJECT-TYPE
            SYNTAX INTEGER
            ACCESS read-only
            STATUS mandatory
            DESCRIPTION
                "Contains the number of free 256 byte buffers."
            ::= { huaweiMemoryMan 30 }


        hwBuffer256Used OBJECT-TYPE
            SYNTAX INTEGER
            ACCESS read-only
            STATUS mandatory
            DESCRIPTION
                "Contains the number of used 256 byte buffers."
            ::= { huaweiMemoryMan 31 }


        hwBuffer256DropCounts OBJECT-TYPE
            SYNTAX INTEGER
            ACCESS read-only
            STATUS mandatory
            DESCRIPTION
                "Contains the number of Drop 256 byte buffers."
            ::= { huaweiMemoryMan 32 }


        hwBuffer256FreeError2 OBJECT-TYPE
            SYNTAX INTEGER
            ACCESS read-only
            STATUS mandatory
            DESCRIPTION
                "Contains the number of Free Error2 256 byte buffers."
            ::= { huaweiMemoryMan 33 }


        hwBuffer256FreeError3 OBJECT-TYPE
            SYNTAX INTEGER
            ACCESS read-only
            STATUS mandatory
            DESCRIPTION
                "Contains the number of Free Error3 256 byte buffers."
            ::= { huaweiMemoryMan 34 }


        hwBuffer256CollectCounts OBJECT-TYPE
            SYNTAX INTEGER
            ACCESS read-only
            STATUS mandatory
            DESCRIPTION
                "Contains the number of Collect 256 byte buffers."
            ::= { huaweiMemoryMan 35 }


        hwBuffer512Size OBJECT-TYPE
            SYNTAX INTEGER
            ACCESS read-only
            STATUS mandatory
            DESCRIPTION
                "Contains the size of 512 byte buffers."
            ::= { huaweiMemoryMan 36 }


        hwBuffer512Total OBJECT-TYPE
            SYNTAX INTEGER
            ACCESS read-only
            STATUS mandatory
            DESCRIPTION
                "Contains the total number of 512 byte buffers."
            ::= { huaweiMemoryMan 37 }


        hwBuffer512Free OBJECT-TYPE
            SYNTAX INTEGER
            ACCESS read-only
            STATUS mandatory
            DESCRIPTION
                "Contains the number of free 512 byte buffers."
            ::= { huaweiMemoryMan 38 }


        hwBuffer512Used OBJECT-TYPE
            SYNTAX INTEGER
            ACCESS read-only
            STATUS mandatory
            DESCRIPTION
                "Contains the number of used 512 byte buffers."
            ::= { huaweiMemoryMan 39 }


        hwBuffer512DropCounts OBJECT-TYPE
            SYNTAX INTEGER
            ACCESS read-only
            STATUS mandatory
            DESCRIPTION
                "Contains the number of Drop 512 byte buffers."
            ::= { huaweiMemoryMan 40 }


        hwBuffer512FreeError2 OBJECT-TYPE
            SYNTAX INTEGER
            ACCESS read-only
            STATUS mandatory
            DESCRIPTION
                "Contains the number of Free Error2 512 byte buffers."
            ::= { huaweiMemoryMan 41 }


        hwBuffer512FreeError3 OBJECT-TYPE
            SYNTAX INTEGER
            ACCESS read-only
            STATUS mandatory
            DESCRIPTION
                "Contains the number of Free Error3 512 byte buffers."
            ::= { huaweiMemoryMan 42 }


        hwBuffer512CollectCounts OBJECT-TYPE
            SYNTAX INTEGER
            ACCESS read-only
            STATUS mandatory
            DESCRIPTION
                "Contains the number of Collect 512 byte buffers."
            ::= { huaweiMemoryMan 43 }


        hwBuffer1024Size OBJECT-TYPE
            SYNTAX INTEGER
            ACCESS read-only
            STATUS mandatory
            DESCRIPTION
                "Contains the size of 1024 byte buffers."
            ::= { huaweiMemoryMan 44 }


        hwBuffer1024Total OBJECT-TYPE
            SYNTAX INTEGER
            ACCESS read-only
            STATUS mandatory
            DESCRIPTION
                "Contains the total number of 1024 byte buffers."
            ::= { huaweiMemoryMan 45 }


        hwBuffer1024Free OBJECT-TYPE
            SYNTAX INTEGER
            ACCESS read-only
            STATUS mandatory
            DESCRIPTION
                "Contains the number of free 1024 byte buffers."
            ::= { huaweiMemoryMan 46 }


        hwBuffer1024Used OBJECT-TYPE
            SYNTAX INTEGER
            ACCESS read-only
            STATUS mandatory
            DESCRIPTION
                "Contains the number of used 1024 byte buffers."
            ::= { huaweiMemoryMan 47 }


        hwBuffer1024DropCounts OBJECT-TYPE
            SYNTAX INTEGER
            ACCESS read-only
            STATUS mandatory
            DESCRIPTION
                "Contains the number of Drop 1024 byte buffers."
            ::= { huaweiMemoryMan 48 }


        hwBuffer1024FreeError2 OBJECT-TYPE
            SYNTAX INTEGER
            ACCESS read-only
            STATUS mandatory
            DESCRIPTION
                "Contains the number of Free Error2 1024 byte buffers."
            ::= { huaweiMemoryMan 49 }


        hwBuffer1024FreeError3 OBJECT-TYPE
            SYNTAX INTEGER
            ACCESS read-only
            STATUS mandatory
            DESCRIPTION
                "Contains the number of Free Error3 1024 byte buffers."
            ::= { huaweiMemoryMan 50 }


        hwBuffer1024CollectCounts OBJECT-TYPE
            SYNTAX INTEGER
            ACCESS read-only
            STATUS mandatory
            DESCRIPTION
                "Contains the number of Collect 1024 byte buffers."
            ::= { huaweiMemoryMan 51 }


        hwBuffer2048Size OBJECT-TYPE
            SYNTAX INTEGER
            ACCESS read-only
            STATUS mandatory
            DESCRIPTION
                "Contains the size of 2048 byte buffers."
            ::= { huaweiMemoryMan 52 }


        hwBuffer2048Total OBJECT-TYPE
            SYNTAX INTEGER
            ACCESS read-only
            STATUS mandatory
            DESCRIPTION
                "Contains the total number of 2048 byte buffers."
            ::= { huaweiMemoryMan 53 }


        hwBuffer2048Free OBJECT-TYPE
            SYNTAX INTEGER
            ACCESS read-only
            STATUS mandatory
            DESCRIPTION
                "Contains the number of free 2048 byte buffers."
            ::= { huaweiMemoryMan 54 }


        hwBuffer2048Used OBJECT-TYPE
            SYNTAX INTEGER
            ACCESS read-only
            STATUS mandatory
            DESCRIPTION
                "Contains the number of used 2048 byte buffers."
            ::= { huaweiMemoryMan 55 }


        hwBuffer2048DropCounts OBJECT-TYPE
            SYNTAX INTEGER
            ACCESS read-only
            STATUS mandatory
            DESCRIPTION
                "Contains the number of Drop 2048 byte buffers."
            ::= { huaweiMemoryMan 56 }


        hwBuffer2048FreeError2 OBJECT-TYPE
            SYNTAX INTEGER
            ACCESS read-only
            STATUS mandatory
            DESCRIPTION
                "Contains the number of Free Error2 2048 byte buffers."
            ::= { huaweiMemoryMan 57 }


        hwBuffer2048FreeError3 OBJECT-TYPE
            SYNTAX INTEGER
            ACCESS read-only
            STATUS mandatory
            DESCRIPTION
                "Contains the number of Free Error3 2048 byte buffers."
            ::= { huaweiMemoryMan 58 }


        hwBuffer2048CollectCounts OBJECT-TYPE
            SYNTAX INTEGER
            ACCESS read-only
            STATUS mandatory
            DESCRIPTION
                "Contains the number of Collect 2048 byte buffers."
            ::= { huaweiMemoryMan 59 }


        hwBuffer4096Size OBJECT-TYPE
            SYNTAX INTEGER
            ACCESS read-only
            STATUS mandatory
            DESCRIPTION
                "Contains the size of 4096 byte buffers."
            ::= { huaweiMemoryMan 60 }


        hwBuffer4096Total OBJECT-TYPE
            SYNTAX INTEGER
            ACCESS read-only
            STATUS mandatory
            DESCRIPTION
                "Contains the total number of 4096 byte buffers."
            ::= { huaweiMemoryMan 61 }


        hwBuffer4096Free OBJECT-TYPE
            SYNTAX INTEGER
            ACCESS read-only
            STATUS mandatory
            DESCRIPTION
                "Contains the number of free 4096 byte buffers."
            ::= { huaweiMemoryMan 62 }


        hwBuffer4096Used OBJECT-TYPE
            SYNTAX INTEGER
            ACCESS read-only
            STATUS mandatory
            DESCRIPTION
                "Contains the number of used 4096 byte buffers."
            ::= { huaweiMemoryMan 63 }


        hwBuffer4096DropCounts OBJECT-TYPE
            SYNTAX INTEGER
            ACCESS read-only
            STATUS mandatory
            DESCRIPTION
                "Contains the number of Drop 4096 byte buffers."
            ::= { huaweiMemoryMan 64 }


        hwBuffer4096FreeError2 OBJECT-TYPE
            SYNTAX INTEGER
            ACCESS read-only
            STATUS mandatory
            DESCRIPTION
                "Contains the number of Free Error2 4096 byte buffers."
            ::= { huaweiMemoryMan 65 }


        hwBuffer4096FreeError3 OBJECT-TYPE
            SYNTAX INTEGER
            ACCESS read-only
            STATUS mandatory
            DESCRIPTION
                "Contains the number of Free Error3 4096 byte buffers."
            ::= { huaweiMemoryMan 66 }


        hwBuffer4096CollectCounts OBJECT-TYPE
            SYNTAX INTEGER
            ACCESS read-only
            STATUS mandatory
            DESCRIPTION
                "Contains the number of Collect 4096 byte buffers."
            ::= { huaweiMemoryMan 67 }


        hwBuffer8192Size OBJECT-TYPE
            SYNTAX INTEGER
            ACCESS read-only
            STATUS mandatory
            DESCRIPTION
                "Contains the size of 8192 byte buffers."
            ::= { huaweiMemoryMan 68 }


        hwBuffer8192Total OBJECT-TYPE
            SYNTAX INTEGER
            ACCESS read-only
            STATUS mandatory
            DESCRIPTION
                "Contains the total number of 8192 byte buffers."
            ::= { huaweiMemoryMan 69 }


        hwBuffer8192Free OBJECT-TYPE
            SYNTAX INTEGER
            ACCESS read-only
            STATUS mandatory
            DESCRIPTION
                "Contains the number of free 8192 byte buffers."
            ::= { huaweiMemoryMan 70 }


        hwBuffer8192Used OBJECT-TYPE
            SYNTAX INTEGER
            ACCESS read-only
            STATUS mandatory
            DESCRIPTION
                "Contains the number of used 8192 byte buffers."
            ::= { huaweiMemoryMan 71 }


        hwBuffer8192DropCounts OBJECT-TYPE
            SYNTAX INTEGER
            ACCESS read-only
            STATUS mandatory
            DESCRIPTION
                "Contains the number of Drop 8192 byte buffers."
            ::= { huaweiMemoryMan 72 }


        hwBuffer8192FreeError2 OBJECT-TYPE
            SYNTAX INTEGER
            ACCESS read-only
            STATUS mandatory
            DESCRIPTION
                "Contains the number of Free Error2 8192 byte buffers."
            ::= { huaweiMemoryMan 73 }


        hwBuffer8192FreeError3 OBJECT-TYPE
            SYNTAX INTEGER
            ACCESS read-only
            STATUS mandatory
            DESCRIPTION
                "Contains the number of Free Error3 8192 byte buffers."
            ::= { huaweiMemoryMan 74 }


        hwBuffer8192CollectCounts OBJECT-TYPE
            SYNTAX INTEGER
            ACCESS read-only
            STATUS mandatory
            DESCRIPTION
                "Contains the number of Collect 8192 byte buffers."
            ::= { huaweiMemoryMan 75 }


        hwBuffer45KSize OBJECT-TYPE
            SYNTAX INTEGER
            ACCESS read-only
            STATUS mandatory
            DESCRIPTION
                "Contains the size of 45K byte buffers."
            ::= { huaweiMemoryMan 76 }


        hwBuffer45KTotal OBJECT-TYPE
            SYNTAX INTEGER
            ACCESS read-only
            STATUS mandatory
            DESCRIPTION
                "Contains the total number of 45K byte buffers."
            ::= { huaweiMemoryMan 77 }


        hwBuffer45KFree OBJECT-TYPE
            SYNTAX INTEGER
            ACCESS read-only
            STATUS mandatory
            DESCRIPTION
                "Contains the number of free 45K byte buffers."
            ::= { huaweiMemoryMan 78 }


        hwBuffer45KUsed OBJECT-TYPE
            SYNTAX INTEGER
            ACCESS read-only
            STATUS mandatory
            DESCRIPTION
                "Contains the number of used 45K byte buffers."
            ::= { huaweiMemoryMan 79 }


        hwBuffer45KDropCounts OBJECT-TYPE
            SYNTAX INTEGER
            ACCESS read-only
            STATUS mandatory
            DESCRIPTION
                "Contains the number of Drop 45K byte buffers."
            ::= { huaweiMemoryMan 80 }


        hwBuffer45KFreeError2 OBJECT-TYPE
            SYNTAX INTEGER
            ACCESS read-only
            STATUS mandatory
            DESCRIPTION
                "Contains the number of Free Error2 45K byte buffers."
            ::= { huaweiMemoryMan 81 }


        hwBuffer45KFreeError3 OBJECT-TYPE
            SYNTAX INTEGER
            ACCESS read-only
            STATUS mandatory
            DESCRIPTION
                "Contains the number of Free Error3 45K byte buffers."
            ::= { huaweiMemoryMan 82 }


        hwBuffer45KCollectCounts OBJECT-TYPE
            SYNTAX INTEGER
            ACCESS read-only
            STATUS mandatory
            DESCRIPTION
                "Contains the number of Collect 45K byte buffers."
            ::= { huaweiMemoryMan 83 }


        hwBuffer256KSize OBJECT-TYPE
            SYNTAX INTEGER
            ACCESS read-only
            STATUS mandatory
            DESCRIPTION
                "Contains the size of 256K byte buffers."
            ::= { huaweiMemoryMan 84 }


        hwBuffer256KTotal OBJECT-TYPE
            SYNTAX INTEGER
            ACCESS read-only
            STATUS mandatory
            DESCRIPTION
                "Contains the total number of 256K byte buffers."
            ::= { huaweiMemoryMan 85 }


        hwBuffer256KFree OBJECT-TYPE
            SYNTAX INTEGER
            ACCESS read-only
            STATUS mandatory
            DESCRIPTION
                "Contains the number of free 256K byte buffers."
            ::= { huaweiMemoryMan 86 }


        hwBuffer256KUsed OBJECT-TYPE
            SYNTAX INTEGER
            ACCESS read-only
            STATUS mandatory
            DESCRIPTION
                "Contains the number of used 256K byte buffers."
            ::= { huaweiMemoryMan 87 }


        hwBuffer256KDropCounts OBJECT-TYPE
            SYNTAX INTEGER
            ACCESS read-only
            STATUS mandatory
            DESCRIPTION
                "Contains the number of Drop 256K byte buffers."
            ::= { huaweiMemoryMan 88 }


        hwBuffer256KFreeError2 OBJECT-TYPE
            SYNTAX INTEGER
            ACCESS read-only
            STATUS mandatory
            DESCRIPTION
                "Contains the number of Free Error2 256K byte buffers."
            ::= { huaweiMemoryMan 89 }


        hwBuffer256KFreeError3 OBJECT-TYPE
            SYNTAX INTEGER
            ACCESS read-only
            STATUS mandatory
            DESCRIPTION
                "Contains the number of Free Error3 256K byte buffers."
            ::= { huaweiMemoryMan 90 }


        hwBuffer256KCollectCounts OBJECT-TYPE
            SYNTAX INTEGER
            ACCESS read-only
            STATUS mandatory
            DESCRIPTION
                "Contains the number of Collect 256K byte buffers."
            ::= { huaweiMemoryMan 91 }


        hwMemoryMallocFail OBJECT-TYPE
            SYNTAX INTEGER
            ACCESS read-only
            STATUS mandatory
            DESCRIPTION
                "The times of memory allocation failures."
            ::= { huaweiMemoryMan 92 }


        hwMemoryMallocNoMem OBJECT-TYPE
            SYNTAX INTEGER
            ACCESS read-only
            STATUS mandatory
            DESCRIPTION
                "The times of memory allocation failures due to no free memory."
            ::= { huaweiMemoryMan 93 }


-- The configuration management mib is defined as follows:
        hwConfigFile OBJECT IDENTIFIER ::= { router 6 }


-- ===============================================
-- Begin define the object of hwRunCfgChangedTime.
-- ===============================================
        hwRunCfgChangedTime OBJECT-TYPE
            SYNTAX TimeTicks
            ACCESS read-only
            STATUS mandatory
            DESCRIPTION
                "
                This object indicates the SysUpTime at which the running cofiguration was last changed.
                When the running configuration is changed but not saved, the
                value of hwRunCfgChangedTime is greater than hwRunCfgSavedTime.
                "
            ::= { hwConfigFile 1 }


-- ===============================================
-- Begin define of hwRunCfgSavedTime
-- ===============================================
        hwRunCfgSavedTime OBJECT-TYPE
            SYNTAX TimeTicks
            ACCESS read-only
            STATUS mandatory
            DESCRIPTION
                "
                This object indicates the SysUpTime at which the running cofiguration was last saved.
                When the running configuration is changed but not saved, the
                value of hwRunCfgChangedTime is greater than hwRunCfgSavedTime.
                "
            ::= { hwConfigFile 2 }


-- ===============================================
-- Begin define of hwStartCfgChangedTime
-- ===============================================
        hwStartCfgChangedTime OBJECT-TYPE
            SYNTAX TimeTicks
            ACCESS read-only
            STATUS mandatory
            DESCRIPTION
                "
                The time of SysUpTime at which the startup configuration
                was last written.
                "
            ::= { hwConfigFile 3 }


-- ===============================================
-- Begin define of hwNetConfigName
-- ===============================================
        hwNetConfigName OBJECT-TYPE
            SYNTAX DisplayString
            ACCESS read-only
            STATUS mandatory
            DESCRIPTION
                "Network configuration file name."
            ::= { hwConfigFile 4 }


-- ===============================================
-- Begin define of hwHostConfigName
-- ===============================================
        hwHostConfigName OBJECT-TYPE
            SYNTAX DisplayString
            ACCESS read-only
            STATUS obsolete
            DESCRIPTION
                "Host configuration file name."
            ::= { hwConfigFile 5 }


-- ===================================================
-- The define of some system private MIB objects
-- =================================================
--


-- System information mib group,include:
-- hwmRouterSerialNO;
-- hwmWhyReboot;
-- hwmHostName;
        hwmSystem OBJECT IDENTIFIER ::= { mlsr 6 }


-- =================================
-- Begin define of hwmRouterSerialNO
-- =================================
        hwmRouterSerialNO OBJECT-TYPE
            SYNTAX DisplayString
            ACCESS read-only
            STATUS mandatory
            DESCRIPTION
                "The router's unique identification."
            ::= { hwmSystem 1 }


-- ==============================
-- Begin define of hwmWhyReboot
-- ==============================
        hwmWhyReboot OBJECT-TYPE
            SYNTAX DisplayString
            ACCESS read-only
            STATUS mandatory
            DESCRIPTION
                "
                Give the reason of the system's reboot.
                If the system has been reboot, the value of
                which is null.
                "
            ::= { hwmSystem 2 }


-- ==============================
-- Begin define of hwmHostName
-- ==============================
        hwmHostName OBJECT-TYPE
            SYNTAX DisplayString
            ACCESS read-only
            STATUS mandatory
            DESCRIPTION
                "
                An  name for this system. By convention, this is the node's
                fully-qualified domain name.
                "
            ::= { hwmSystem 3 }


        hwmHostHwVersion OBJECT-TYPE
            SYNTAX DisplayString
            ACCESS read-only
            STATUS mandatory
            DESCRIPTION
                "The haredware version of the router."
            ::= { hwmSystem 4 }

    END
