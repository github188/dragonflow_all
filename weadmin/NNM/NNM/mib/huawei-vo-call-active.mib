-- ==========================================================================
-- Copyright (C) 2002 by  HUAWEI TECHNOLOGIES. All rights reserved.
--
-- Description: The purpose of this MIB file is to provide the define of
--              voice call active MIB of HUAWEI quidway serial router,
--              which are used to save the past voice call active information.
-- Reference:
-- ==========================================================================
HUAWEI-VO-CALL-ACTIVE-MIB DEFINITIONS ::= BEGIN

	IMPORTS
		OBJECT-TYPE, MODULE-IDENTITY, IpAddress
			FROM SNMPv2-SMI
		voice
			FROM HUAWEI-3COM-OID-MIB;	
	
		
		hwVoiceCallActiveMIB MODULE-IDENTITY 
			LAST-UPDATED "200410200000Z"		-- Oct 20, 2004  GMT
			ORGANIZATION 
				"Huawei-3COM Technologies Co., Ltd."
			CONTACT-INFO 
				"PLAT Team Huawei 3Com Technologies co.,Ltd.								
				Shang-Di Information Industry Base,
				Hai-Dian District Beijing P.R. China
				http://www.huawei-3com.com
				Zip:100085"
			DESCRIPTION 
				" "
			REVISION "200404081345Z"		-- April 08, 2004 at 13:45 GMT
			DESCRIPTION 
				""
			::= { voice 6 }

		
		hwVoCallActiveObjects OBJECT IDENTIFIER ::= { hwVoiceCallActiveMIB 1 }

		
--  Voice Call Active Table
		hwVoCallActiveTable OBJECT-TYPE
			SYNTAX SEQUENCE OF HWVoCallActiveEntry
			MAX-ACCESS not-accessible
			STATUS current
			DESCRIPTION
				"The table contains the Voice Active Call information ."
			::= { hwVoCallActiveObjects 1 }

		
		hwVoCallActiveEntry OBJECT-TYPE
			SYNTAX HWVoCallActiveEntry
			MAX-ACCESS not-accessible
			STATUS current
			DESCRIPTION
				"The information regarding a single Connection."
			INDEX { hwVoCallActiveChannel }
			::= { hwVoCallActiveTable 1 }

		
		HWVoCallActiveEntry ::=
			SEQUENCE { 
				hwVoCallActiveChannel
					INTEGER,
				hwVoCallActiveCallerNumber
					OCTET STRING,
				hwVoCallActiveCalledNumber
					OCTET STRING,
				hwVoCallActiveEncodeType
					INTEGER,
				hwVoCallActiveLocalAddress
					IpAddress,
				hwVoCallActivePeerAddress
					IpAddress,
				hwVoCallActiveCallOrigin
					INTEGER,
				hwVoCallActiveIPSigType
					INTEGER,
				hwVoCallActivePSTNSigType
					INTEGER,
				hwVoCallActiveStatus
					INTEGER
			 }

		hwVoCallActiveChannel OBJECT-TYPE
			SYNTAX INTEGER
			MAX-ACCESS read-only
			STATUS current
			DESCRIPTION
				"The logic channel number this call is going through. "
			::= { hwVoCallActiveEntry 1 }

		
		hwVoCallActiveCallerNumber OBJECT-TYPE
			SYNTAX OCTET STRING (SIZE (0..31))
			MAX-ACCESS read-only
			STATUS current
			DESCRIPTION
				"The calling number for this  call."
			::= { hwVoCallActiveEntry 2 }

		
		hwVoCallActiveCalledNumber OBJECT-TYPE
			SYNTAX OCTET STRING (SIZE (0..31))
			MAX-ACCESS read-only
			STATUS current
			DESCRIPTION
				"The number this  call   is connected to."
			::= { hwVoCallActiveEntry 3 }

		
		hwVoCallActiveEncodeType OBJECT-TYPE
			SYNTAX INTEGER
				{
				g711a(1),
				g711u(2),
				g723(3),
				g729(4),
				g729a(5),
				unknown(0)
				}
			MAX-ACCESS read-only
			STATUS current
			DESCRIPTION
				"This object specifies the encode type which is used by this call."
			::= { hwVoCallActiveEntry 4 }

		
		hwVoCallActiveLocalAddress OBJECT-TYPE
			SYNTAX IpAddress
			MAX-ACCESS read-only
			STATUS current
			DESCRIPTION
				"The local TCP address this call is using ."
			::= { hwVoCallActiveEntry 5 }

		
		hwVoCallActivePeerAddress OBJECT-TYPE
			SYNTAX IpAddress
			MAX-ACCESS read-only
			STATUS current
			DESCRIPTION
				"The peer TCP address this call is using ."
			::= { hwVoCallActiveEntry 6 }

		
		hwVoCallActiveCallOrigin OBJECT-TYPE
			SYNTAX INTEGER
				{
				caller(1),
				called(2)
				}
			MAX-ACCESS read-only
			STATUS current
			DESCRIPTION
				"The origin of this call ,means the local gateway or 
				the peer gateway ."
			::= { hwVoCallActiveEntry 7 }

		
		hwVoCallActiveIPSigType OBJECT-TYPE
			SYNTAX INTEGER { h323(1) }
			MAX-ACCESS read-only
			STATUS current
			DESCRIPTION
				"The IP signaling type this call is using ."
			::= { hwVoCallActiveEntry 8 }

		
		hwVoCallActivePSTNSigType OBJECT-TYPE
			SYNTAX INTEGER
				{
				fxs(1),
				fxo(2),
				em(3),
				r2(4),
				dss1(5),
				dem(6),
				unknown(0)
				}
			MAX-ACCESS read-only
			STATUS current
			DESCRIPTION
				"The PSTN signaling type this call is using ."
			::= { hwVoCallActiveEntry 9 }

		
		hwVoCallActiveStatus OBJECT-TYPE
			SYNTAX INTEGER
				{
				idle(1),
				calling(2),
				alerting(3),
				talking(4),
				release(5)
				}
			MAX-ACCESS read-only
			STATUS current
			DESCRIPTION
				"The current progress status of this call ."
			::= { hwVoCallActiveEntry 10 }

		
	
	END
