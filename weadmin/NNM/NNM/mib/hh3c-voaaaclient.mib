-- ==========================================================================
-- Copyright (C) 2006 by H3C Technologies. All rights reserved.
--
-- Description: The voice AAA client MIB for remote dialing users'
--              Authentication, Authorization and Accounting.
--
-- Reference:
-- ==========================================================================
HH3C-VOAAACLIENT-MIB DEFINITIONS ::= BEGIN
    IMPORTS
        OBJECT-TYPE, MODULE-IDENTITY, Integer32
            FROM SNMPv2-SMI
        RowStatus,TruthValue
            FROM SNMPv2-TC
        hh3cVoice
            FROM HH3C-OID-MIB;

    hh3cVoiceAAAClient MODULE-IDENTITY
        LAST-UPDATED "200603270000Z"   -- Mar 27, 2006  GMT
        ORGANIZATION
            "Hangzhou H3C Tech. Co., Ltd."
        CONTACT-INFO
            "Platform Team Hangzhou H3C Tech. Co., Ltd.
            Hai-Dian District Beijing P.R. China
            http://www.h3c.com
            Zip:100085
            "
        DESCRIPTION
            "This MIB file defines the voice AAA client MIB for remote
            dialing users' Authentication, Authorization and Accounting."
        REVISION "200603270000Z"       -- Mar 27, 2006  GMT
        DESCRIPTION
            "The initial version of this MIB file."
        ::= { hh3cVoice 9 }


    hh3cVoAAAClientObjects OBJECT IDENTIFIER ::= { hh3cVoiceAAAClient 1 }


-- AAA Client Configuration Object Group
--
-- The objects in this group describe and store the configuration parameters
-- on the AAA Client function of this gateway which based on Authentication,
-- Authorization, Accounting protocols.
    hh3cVoAAAClientCfgObjects OBJECT IDENTIFIER ::= { hh3cVoAAAClientObjects 1 }

    hh3cVoAAAGwAuthenDid OBJECT-TYPE
        SYNTAX TruthValue
        MAX-ACCESS read-write
        STATUS current
        DESCRIPTION
            "Enable or disable the function of authentication
            for Direct Inward Dialing."
        DEFVAL { false }
        ::= { hh3cVoAAAClientCfgObjects 1 }

    hh3cVoAAAGwAuthorDid OBJECT-TYPE
        SYNTAX TruthValue
        MAX-ACCESS read-write
        STATUS current
        DESCRIPTION
            "Enable or disable the function of authorization for Direct
            Inward Dialing on condition that the function of authentication
            is enabled."
        DEFVAL { false }
        ::= { hh3cVoAAAClientCfgObjects 2 }

    hh3cVoAAAGwAccountingDid OBJECT-TYPE
        SYNTAX TruthValue
        MAX-ACCESS read-write
        STATUS current
        DESCRIPTION
            "Enable or disable the function of accounting for
            Direct Inward Dialing."
        DEFVAL { false }
        ::= { hh3cVoAAAClientCfgObjects 3 }

    hh3cVoAAAGwAccountMethod OBJECT-TYPE
        SYNTAX INTEGER
            {
                startAck(1),
                startNoAck(2),
                stopOnly(3)
            }
        MAX-ACCESS read-write
        STATUS current
        DESCRIPTION
            "Specify the sending mode of accounting packets of this gateway.
            startAck: send starting and stopping accounting packets and wait
                for the acknowledge of RADIUS server.
            startNoAck: send starting and stopping accounting packets
                without waiting for the acknowledge of RADIUS server.
            stopOnly: send stopping accounting packets and wait
                for the acknowledge of RADIUS server."
        DEFVAL { startNoAck }
        ::= { hh3cVoAAAClientCfgObjects 4 }

-- AAA Gateway Access Number Table
--
-- Table to store the AAA access number and the dialing process attribute
-- of this gateway, which includes the access number, the card digits, the
-- password digits,the redialing times and so on.
    hh3cVoAAAGwAccessNumberTable OBJECT-TYPE
        SYNTAX SEQUENCE OF Hh3cVoAAAGwAccessNumberEntry
        MAX-ACCESS not-accessible
        STATUS current
        DESCRIPTION
            "The table contains the information of the AAA access number for
            Two-stage Dialing, which includes the configuration of
            authentication, authorization, accounting, the dialing process,
            the length of card number, the length of password ,
            the redialing times."
        ::= { hh3cVoAAAClientObjects 2 }

    hh3cVoAAAGwAccessNumberEntry OBJECT-TYPE
        SYNTAX Hh3cVoAAAGwAccessNumberEntry
        MAX-ACCESS not-accessible
        STATUS current
        DESCRIPTION
            "The information of the access number."
        INDEX { hh3cVoAAAGwAccessNumber }
        ::= { hh3cVoAAAGwAccessNumberTable 1 }

    Hh3cVoAAAGwAccessNumberEntry ::=
        SEQUENCE
            {
                hh3cVoAAAGwAccessNumber OCTET STRING,
                hh3cVoAAAGwAuthentication TruthValue,
                hh3cVoAAAGwAuthorization TruthValue,
                hh3cVoAAAGwAccounting TruthValue,
                hh3cVoAAAGwProcessConfig INTEGER,
                hh3cVoAAAGwCardDigit Integer32,
                hh3cVoAAAGwPasswordDigit Integer32,
                hh3cVoAAAGwRedialTimes Integer32,
                hh3cVoAAAGwRowStatus RowStatus
             }

    hh3cVoAAAGwAccessNumber OBJECT-TYPE
        SYNTAX OCTET STRING (SIZE (1..31))
        MAX-ACCESS not-accessible
        STATUS current
        DESCRIPTION
            "The access number of the AAA client.
            The access number can be composed of digits, wildcards
            or the letter 'T'.
            If digits, wildcards and the letter 'T'
            are all included in an access number, the wildcards must
            follow digits and appear at the end, and 'T' must be the
            last character and appear only once.
            In addition, an access number can include only wildcards,
            or only one 'T'."
        ::= { hh3cVoAAAGwAccessNumberEntry 1 }

    hh3cVoAAAGwAuthentication OBJECT-TYPE
        SYNTAX TruthValue
        MAX-ACCESS read-create
        STATUS current
        DESCRIPTION
            "Enable or disable the function of authentication for
            Two-stage Dialing."
        DEFVAL { false }
        ::= { hh3cVoAAAGwAccessNumberEntry 2 }

    hh3cVoAAAGwAuthorization OBJECT-TYPE
        SYNTAX TruthValue
        MAX-ACCESS read-create
        STATUS current
        DESCRIPTION
            "Enable or disable the function of authorization
            for Two-stage Dialing on condition that the function
            of authentication is enabled."
        DEFVAL { false }
        ::= { hh3cVoAAAGwAccessNumberEntry 3 }

    hh3cVoAAAGwAccounting OBJECT-TYPE
        SYNTAX TruthValue
        MAX-ACCESS read-create
        STATUS current
        DESCRIPTION
            "Enable or disable the function of accounting for
            Two-stage Dialing."
        DEFVAL { false }
        ::= { hh3cVoAAAGwAccessNumberEntry 4 }

    hh3cVoAAAGwProcessConfig OBJECT-TYPE
        SYNTAX INTEGER
            {
                callerNumber(1),
                cardNumber(2),
                callerNumIvr(3)
            }
        MAX-ACCESS read-create
        STATUS current
        DESCRIPTION
            "The dialing process type of this access number.
            callerNumber: caller number dialing process without IVR
                (Interactive Voice Reponse), that is, caller number's
                authentication for Two-stage Dialing process
                without IVR.
            cardNumber: card number dialing process with IVR, that is,
                card number and password's authentication for
                Two-stage Dialing process with IVR.
            callerNumIvr: caller number dialing process with IVR,
                that is, caller number's authentication for
                Two-stage Dialing process with IVR."
        DEFVAL { callerNumIvr }
        ::= { hh3cVoAAAGwAccessNumberEntry 5 }

    hh3cVoAAAGwCardDigit OBJECT-TYPE
        SYNTAX Integer32 (1..31)
        MAX-ACCESS read-create
        STATUS current
        DESCRIPTION
            "The length of card number only for the cardNumber
            dialing process."
        DEFVAL { 12 }
        ::= { hh3cVoAAAGwAccessNumberEntry 6 }

    hh3cVoAAAGwPasswordDigit OBJECT-TYPE
        SYNTAX Integer32 (1..16)
        MAX-ACCESS read-create
        STATUS current
        DESCRIPTION
            "The length of password only for the cardNumber
            dialing process."
        DEFVAL { 6 }
        ::= { hh3cVoAAAGwAccessNumberEntry 7 }

    hh3cVoAAAGwRedialTimes OBJECT-TYPE
        SYNTAX Integer32 (0..10)
        MAX-ACCESS read-create
        STATUS current
        DESCRIPTION
            "The redialing times of inputing card number or
            password or called number for the cardNumber dialing process,
            or the redialing times of inputing called number
            for the callerNumIvr dialing process."
        DEFVAL { 2 }
        ::= { hh3cVoAAAGwAccessNumberEntry 8 }

    hh3cVoAAAGwRowStatus OBJECT-TYPE
        SYNTAX RowStatus
        MAX-ACCESS read-create
        STATUS current
        DESCRIPTION
            "The row status of this table."
        ::= { hh3cVoAAAGwAccessNumberEntry 9 }
END
