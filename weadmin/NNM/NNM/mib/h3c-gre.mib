-- =================================================================
-- Copyright (C) 2005 by  HUAWEI 3COM TECHNOLOGIES. All rights reserved.
--
-- Description: Generic Routing Encapsulation configuration MIB
-- Reference: IF-MIB
-- =================================================================
H3C-GRE-MIB DEFINITIONS ::= BEGIN

IMPORTS
    h3cCommon
        FROM HUAWEI-3COM-OID-MIB
    Unsigned32, OBJECT-TYPE, MODULE-IDENTITY
        FROM SNMPv2-SMI
    ifIndex
        FROM IF-MIB; 

h3cGre MODULE-IDENTITY
    LAST-UPDATED
        "200506040000Z"                        -- June 4, 2005 at 00:00 GMT
    ORGANIZATION
        "Huawei 3Com Technologies Co., Ltd.
        "
    CONTACT-INFO
        "Platform Team Huawei 3Com Technologies Co., Ltd.
        Hai-Dian District Beijing P.R. China
        http://www.huawei-3com.com
        Zip:100085
        "
    DESCRIPTION
        "This MIB contains objects to Manage configuration and 
        Monitor running state for GRE.
        "                        
    REVISION
        "200506040000Z"                        -- June 4, 2005 at 00:00 GMT
    DESCRIPTION
        "The initial revision of this MIB module.
        "
    ::= { h3cCommon 54 }

    h3cGreObjects OBJECT IDENTIFIER ::= { h3cGre 1 }

    h3cGreTable  OBJECT-TYPE
    SYNTAX SEQUENCE OF H3cGreEntry
    MAX-ACCESS not-accessible
    STATUS current
    DESCRIPTION
        "A table of Generic Routing Encapsulation(GRE) configuration. 
        It contains configuration of GRE Key, and enable flags of Key
        and Checksum. The detail of Key and Checksum is described in
        RFC2784 and RFC2890.
        "
    ::= { h3cGreObjects 1 }
                        
    h3cGreEntry OBJECT-TYPE
    SYNTAX H3cGreEntry
    MAX-ACCESS not-accessible
    STATUS current
    DESCRIPTION
        "The entry of h3cGreTable
        "
    INDEX { ifIndex }
    ::= { h3cGreTable 1 }

    H3cGreEntry ::= SEQUENCE {
        h3cGreKeyValue
            Unsigned32, 
        h3cGreKey
            INTEGER, 
        h3cGreChecksum
            INTEGER
    }
    h3cGreKeyValue OBJECT-TYPE
    SYNTAX Unsigned32
    MAX-ACCESS read-write
    STATUS current
    DESCRIPTION
        "The value of GRE key
        "
    ::= { h3cGreEntry 1 }
                     
    h3cGreKey OBJECT-TYPE
        SYNTAX INTEGER{
            enable(1), 
            disable(2)
        }
        MAX-ACCESS read-write
        STATUS current
        DESCRIPTION
        "The enable flag of GRE key
        "
    ::= { h3cGreEntry 2 }
                        
    h3cGreChecksum OBJECT-TYPE
        SYNTAX INTEGER{
            enable(1), 
            disable(2)
        }
        MAX-ACCESS read-write
        STATUS current
        DESCRIPTION
            "The enable flag of GRE Checksum
            "
        ::= { h3cGreEntry 3 }

END
