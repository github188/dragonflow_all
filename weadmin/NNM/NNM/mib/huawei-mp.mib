-- =================================================================
-- Copyright (C) 2004 by  HUAWEI 3COM TECHNOLOGIES. All rights reserved
-- 
-- Description: This mib file is used for inquiring for MP (Multilink PPP)
--              link status information.
-- Reference:
-- =================================================================

HUAWEI-MP-MIB DEFINITIONS ::= BEGIN

        IMPORTS
            ifIndex			
                FROM RFC1213-MIB
            huaweiMgmt,huaweiDatacomm
                FROM HUAWEI-3COM-OID-MIB                                                     
            OBJECT-GROUP, MODULE-COMPLIANCE                 
                FROM SNMPv2-CONF                        
            Integer32, Counter32, OBJECT-TYPE, MODULE-IDENTITY                   
                FROM SNMPv2-SMI
            TEXTUAL-CONVENTION, DisplayString
                FROM SNMPv2-TC;        

        hwMultilinkPPP MODULE-IDENTITY 
                LAST-UPDATED "200405180000Z"            -- May 18, 2004 at 00:00 GMT
                ORGANIZATION 
                        "Huawei Technologies co.,Ltd."
                CONTACT-INFO 
                        " R&D BeiJing, Huawei-3Com Technologies co.,Ltd.
                        Huawei Bld.,NO.3 Xinxi Rd., 
                        Shang-Di Information Industry Base,
                        Hai-Dian District Beijing P.R. China
                        Zip:100085 
                        Http://www.huawei-3com.com
                        E-mail:support@huawei-3com.com "
                DESCRIPTION 
                        "The HUAWEI-MP-MIB provides read access to MP(Multilink PPP) link
                        status information. The information available through this MIB includes:
                        the father channel, the bundled son channel, the slot on which MP bundled, 
                        the number of son channels, the bundle name,
                        the statistic of lost fragments, reordered packets, unassigned packets, 
                        interleaved packets, and the received/sent sequence, etc.
                        "
                ::= { huaweiDatacomm 33 }

--
-- Node definitions
--        
        
        hwMpObjects OBJECT IDENTIFIER ::= { hwMultilinkPPP  1 }
        
        hwMpMultilinkTable OBJECT-TYPE
                SYNTAX SEQUENCE OF HwMpMultilinkEntry
                MAX-ACCESS not-accessible
                STATUS current
                DESCRIPTION
                        "This table describes the information of MP link. 
                        The index of this table is the interface index of MP group or 
                        VT(Virtual Template)."
                ::= { hwMpObjects 1 }

        hwMpMultilinkEntry OBJECT-TYPE
                SYNTAX HwMpMultilinkEntry
                MAX-ACCESS not-accessible
                STATUS current
                DESCRIPTION
                        "Each entry in this table describes the information of MP link.
                        The available information includes: 
                        the father channel, the slot on which MP bundled, 
                        the number of bundled son channels, 
                        the statistics of lost fragments, reordered packets, 
                        unassigned packets, interleaved packets, 
                        and received/sent sequence.                         
                        "
                INDEX { ifIndex }
                ::= { hwMpMultilinkTable 1 }
        
        HwMpMultilinkEntry ::=
                SEQUENCE {
                        hwMpMultilinkDescr
                                DisplayString,   
                        hwMpBundleName
                                DisplayString,                                               
                        hwMpBundledSlot
                                Integer32,
                        hwMpBundledMemberCnt
                                Integer32,
			hwMpLostFragments
				Counter32,
			hwMpReorderedPkts
				Counter32,
			hwMpUnassignedPkts
				Counter32,
			hwMpInterleavedPkts
				Counter32,
			hwMpRcvdSequence
				Integer32,
			hwMpSentSequence
				Integer32																														
                 } 
                                         
        hwMpMultilinkDescr OBJECT-TYPE
                SYNTAX DisplayString
                MAX-ACCESS read-only
                STATUS current
                DESCRIPTION
                        "The interface name of the father interface on which MP bundled. 
                        It is the name of a Virtual Temblate or a MP group."
                ::= { hwMpMultilinkEntry 1 } 
                
        hwMpBundleName OBJECT-TYPE
                SYNTAX DisplayString
                MAX-ACCESS read-only
                STATUS current
                DESCRIPTION
                        "The bundle name of the multilink. 
                        when authentication is configured, the bundle name is the authenticated
                        user name; when authentication not configured, the bundle name is
                        multilink.
                        "
                ::= { hwMpMultilinkEntry 2 }                 
                
        hwMpBundledSlot OBJECT-TYPE
                SYNTAX Integer32
                MAX-ACCESS read-only
                STATUS current
                DESCRIPTION
                        "The slot on which MP bundled. 
                        "
                ::= { hwMpMultilinkEntry 3 }
        
        hwMpBundledMemberCnt OBJECT-TYPE
                SYNTAX Integer32
                MAX-ACCESS read-only
                STATUS current
                DESCRIPTION
                        "The number of the bundled son channel of the MP link. "
                ::= { hwMpMultilinkEntry 4 }

        hwMpLostFragments OBJECT-TYPE
                SYNTAX Counter32
                MAX-ACCESS read-only
                STATUS current
                DESCRIPTION
                        "The number of fragments of the MP link discarded because 
                        bad fragments received, or assembling packet failed, etc."
                ::= { hwMpMultilinkEntry 5 }

         hwMpReorderedPkts OBJECT-TYPE
                SYNTAX Counter32
                MAX-ACCESS read-only
                STATUS current
                DESCRIPTION
                        "The number of received packets of the MP link reordered.
                        "
                ::= { hwMpMultilinkEntry 6 }                       

         hwMpUnassignedPkts OBJECT-TYPE
                SYNTAX Counter32
                MAX-ACCESS read-only
                STATUS current
                DESCRIPTION
                        "The number of received packets of the MP link waiting for reordering.
                        "
                ::= { hwMpMultilinkEntry 7 }      
                
         hwMpInterleavedPkts OBJECT-TYPE
                SYNTAX Counter32
                MAX-ACCESS read-only
                STATUS current
                DESCRIPTION
                        "The number of received packets of the MP link interleaved by the 
                        packets queued in RTPQ(Real-time Transport Protocol Queue) or 
                        LLQ(Low Latency Queue).
                        "
                ::= { hwMpMultilinkEntry 8 }  
                
         hwMpRcvdSequence OBJECT-TYPE
                SYNTAX Integer32
                MAX-ACCESS read-only
                STATUS current
                DESCRIPTION
                        "The current sequence number of the MP link for receiving.
                        "
                ::= { hwMpMultilinkEntry 9 }   

         hwMpSentSequence OBJECT-TYPE
                SYNTAX Integer32
                MAX-ACCESS read-only
                STATUS current
                DESCRIPTION
                        "The current sequence number of the MP link for sending.
                        "
                ::= { hwMpMultilinkEntry 10 }


        hwMpMemberlinkTable OBJECT-TYPE
                SYNTAX SEQUENCE OF HwMpMemberlinkEntry
                MAX-ACCESS not-accessible
                STATUS current
                DESCRIPTION
                        "This table describes the information of son channels of the MP link.
                        The index of this table is the interface index of MP group or
                        VT(Virtual Template). 
                        "
                ::= { hwMpObjects 2 }

        hwMpMemberlinkEntry OBJECT-TYPE
                SYNTAX HwMpMemberlinkEntry
                MAX-ACCESS not-accessible
                STATUS current
                DESCRIPTION
                        "Each entry in this table describes the information of the bundled
                        son channels of MP link. The available information includes: 
                        the interface index of the son channel, 
                        the interface name of the son channel.
                        "
                INDEX { ifIndex, hwMpMemberlinkSeqNumber }
                ::= { hwMpMemberlinkTable 1 }
        
        HwMpMemberlinkEntry ::=
                SEQUENCE {
                        hwMpMemberlinkSeqNumber
                                Integer32,
                        hwMpMemberlinkIfIndex
                                Integer32,
                        hwMpMemberlinkDescr
                                DisplayString,
                        hwMpMemberlinkMpStatus
                                Integer32																													
                 } 

        hwMpMemberlinkSeqNumber OBJECT-TYPE
                SYNTAX Integer32
                MAX-ACCESS read-only
                STATUS current
                DESCRIPTION
                        "The bundled sequence number of the son channels of the MP link.
                        This object is one of the index of the table.
                        "
                ::= { hwMpMemberlinkEntry 1 }  

        hwMpMemberlinkIfIndex OBJECT-TYPE
                SYNTAX Integer32
                MAX-ACCESS read-only
                STATUS current
                DESCRIPTION
                        "The interface index of the son channels of the MP link.
                        "
                ::= { hwMpMemberlinkEntry 2 } 
                
        hwMpMemberlinkDescr OBJECT-TYPE
                SYNTAX DisplayString
                MAX-ACCESS read-only
                STATUS current
                DESCRIPTION
                        "The interface name of the son channels of the MP link.
                        "
                ::= { hwMpMemberlinkEntry 3 } 
                
        hwMpMemberlinkMpStatus OBJECT-TYPE
                SYNTAX Integer32
                MAX-ACCESS read-only
                STATUS current
                DESCRIPTION
                        "The MP status of the son channels of the MP link.
                        "
                ::= { hwMpMemberlinkEntry 4 } 
                                
         hwMpNotifications OBJECT IDENTIFIER ::= { hwMultilinkPPP 2 }

         
         hwMpConformance OBJECT IDENTIFIER ::= { hwMultilinkPPP 3 }

         
         hwMpCompliances OBJECT IDENTIFIER ::= { hwMpConformance 1 }

         
         hwMpCompliance MODULE-COMPLIANCE
                 STATUS current
                 DESCRIPTION 
                         "The compliance statement for entities which 
                         implement the Huawei Multilink PPP mib."
                 MODULE -- this module
                         MANDATORY-GROUPS { hwMpMandatoryGroup }
                 ::= { hwMpCompliances 1 }

         
         hwMpGroups OBJECT IDENTIFIER ::= { hwMpConformance 2 }

         
         hwMpMandatoryGroup OBJECT-GROUP
                 OBJECTS { hwMpBundledMemberCnt, hwMpMemberlinkSeqNumber, hwMpMemberlinkIfIndex }
                 STATUS current
                 DESCRIPTION 
                         "A collection of objects providing mandatory MP information."
                 ::= { hwMpGroups 1 }
         
         hwMpInfoGroup OBJECT-GROUP
                 OBJECTS { hwMpMultilinkDescr, hwMpBundleName, 
                         hwMpBundledSlot, hwMpBundledMemberCnt,
                         hwMpLostFragments, hwMpReorderedPkts, 
                         hwMpUnassignedPkts, hwMpInterleavedPkts, 
                         hwMpRcvdSequence, hwMpSentSequence,
                         hwMpMemberlinkDescr,hwMpMemberlinkMpStatus }
                 STATUS current
                 DESCRIPTION 
                         "All running information of MP feature."
                 ::= { hwMpGroups 2 }                                                                                        
                                                                                                                                                                                    
   END
