-- =============================================================================
-- Copyright (C) 2006-2007 by H3C TECHNOLOGIES.  All rights reserved.
--
-- Description:
--   The file defines a MIB to provide WLAN configuration information.
-- Reference:
-- =============================================================================
HH3C-DOT11-CFG-MIB DEFINITIONS ::= BEGIN

IMPORTS
        TruthValue,
        RowStatus
    FROM SNMPv2-TC
        MODULE-IDENTITY,
        OBJECT-TYPE,
        Integer32,
        Unsigned32
    FROM SNMPv2-SMI
        hh3cDot11,
        Hh3cDot11RadioType,
        Hh3cDot11TxPwrLevelScopeType,
        Hh3cDot11ChannelScopeType,
        Hh3cDot11SSIDStringType,
        Hh3cDot11AuthenType,
        Hh3cDot11RadioScopeType,
        Hh3cDot11SSIDEncryptModeType,
        Hh3cDot11SecIEStatusType,
        Hh3cDot11PreambleType,
        Hh3cDot11ServicePolicyIDType,
        Hh3cDot11TunnelSecSchemType
    FROM HH3C-DOT11-REF-MIB;

hh3cDot11CFG MODULE-IDENTITY
    LAST-UPDATED "200802251800Z"        -- Feb 25, 2008 at 18:00 GMT
    ORGANIZATION
        "Hangzhou H3C Technologies Co., Ltd."
    CONTACT-INFO
        "Platform Team Hangzhou H3C Technologies Co., Ltd.
         Hai-Dian District Beijing P.R. China
         Http://www.h3c.com
         Zip:100085"
    DESCRIPTION
        "This MIB provides information about WLAN configuration.

        GLOSSARY

        IEEE 802.11
        Standard to encourage interoperability among
        wireless networking equipment.

        Access point (AP)
        Transmitter/receiver (transceiver) device
        that commonly connects and transports data
        between a wireless network and a wired network.

        Access control (AC)
        To control and manage multi-APs, it will bridge
        wireless and wired network.

        Fat AP
        Applied in the home, SOHO and so on, and it could
        work independently without help from AC.

        Fit AP
        Applied in the enterprise environment, it will work
        under the control and management from AC.

        Control And Provisioning of Wireless Access Points Protocol
        The short name of protocol is CAPWAP. AC will control
        and manage AP by CAPWAP tunnel protocol defined by IETF.
        Also, a data tunnel will be set up between AC and AP.

        BSS
        IEEE 802.11 Basic Service Set (Radio Cell).  The
        BSS of an AP comprises of the stations directly
        associating with the AP.

        Radio
        The chip set to receive and send wireless signal.

        Association
        The service used to establish access point
        or station mapping and enable station invocation
        of the distribution system services.
        (Wireless clients attempt to connect to
        access points.)

        Basic Rate
        A data rate that is mandatory for client
        devices to support in order for them to achieve
        successful association.

        MSDU
        MAC Service Data Unit, it is frame format defined by
        802.11.

        TU
        It is 1,024 microseconds (ms), which is about 1
        millisecond.

        AKM
        The authentication and key management method defined by
        802.11i, and which includes 802.1x and pre-shared key."

    REVISION "200802251800Z"        -- Feb 25, 2008 at 18:00 GMT
    DESCRIPTION
        "Modified to add new nodes."
    REVISION "200712211800Z"        -- Dec 21, 2007 at 18:00 GMT
    DESCRIPTION
        "Modified to add new nodes."
    REVISION "200710091655Z"    -- October 09, 2007 at 16:55 GMT
    DESCRIPTION
        "changed for new requirements"
    REVISION "200706191800Z"        -- June 19, 2007 at 18:00 GMT
    DESCRIPTION
        "Modified to add new table."
    REVISION "200704272000Z"        -- Apr 27, 2007 at 20:00 GMT
    DESCRIPTION
        "Modified to fix some issue."
    REVISION "200702012000Z"        -- February 01, 2007 at 20:00 GMT
    DESCRIPTION
        "Modified to support fat AP."
    REVISION "200605101900Z"        -- May 10, 2006 at 19:00 GMT
    DESCRIPTION
        "The initial revision of this MIB module."
    ::= { hh3cDot11 4 }

-- *****************************************************************************
-- *  Major sections
-- *****************************************************************************
--  AP Configuration Group
--  DEFINED AS "The group to provide the configuration information
--  for APs.
hh3cDot11GlobeConfigGroup OBJECT IDENTIFIER  ::= { hh3cDot11CFG 1 }

hh3cDot11PolicyConfigGroup OBJECT IDENTIFIER ::= { hh3cDot11CFG 2 }
--  Policy Configuration Group has the following children:
--  hh3cDot11RadioPolicyTable            ::= { hh3cDot11PolicyConfigGroup 1 }
--  hh3cDot11ServicePolicyTable          ::= { hh3cDot11PolicyConfigGroup 2 }
--  hh3cDot11ServicePolicyExtTable       ::= { hh3cDot11PolicyConfigGroup 3 }

hh3cDot11APConfigGroup OBJECT IDENTIFIER     ::= { hh3cDot11CFG 3 }
--  AP Configuration Group has the following children:
--  hh3cDot11APTemplateTable                 ::= { hh3cDot11APConfigGroup 1 }
--  hh3cDot11RadioToConfigTable              ::= { hh3cDot11APConfigGroup 2 }
--  hh3cDot11APServiceSetTable               ::= { hh3cDot11APConfigGroup 3 }

hh3cDot11RadioIntfConfigGroup OBJECT IDENTIFIER ::= { hh3cDot11CFG 4 }
--  Radio Interface Group has the following children:
--  hh3cDot11RadioIntfConfigTable          ::= { hh3cDot11RadioIntfConfigGroup 1 }
--  hh3cDot11RadioIntfBindTable            ::= { hh3cDot11RadioIntfConfigGroup 2 }

hh3cDot11DataRateConfigGroup OBJECT IDENTIFIER ::= { hh3cDot11CFG 5 }
--  Data Rate Config Group has the following children:
--  hh3cDot11DataRateConfigTable           ::= { hh3cDot11DataRateConfigGroup 1 }

hh3cDot11InterfaceConfigGroup OBJECT IDENTIFIER ::= { hh3cDot11CFG 6 }
--  Interface Config Group has the following children:
--  hh3cDot11WlanEssIfTable               ::= { hh3cDot11InterfaceConfigGroup 1 }
--  hh3cDot11WlanBssIfTable               ::= { hh3cDot11InterfaceConfigGroup 2 }
--  hh3cDot11WLANEthernetIfTable          ::= { hh3cDot11InterfaceConfigGroup 3 }

-- *****************************************************************************
-- *  hh3cDot11GlobeConfigGroup Definition
-- *****************************************************************************
hh3cDot11GlobalCountryCode OBJECT-TYPE
    SYNTAX      OCTET STRING(SIZE(3))
    MAX-ACCESS  read-write
    STATUS      current
    DESCRIPTION
        "Represents the country code for wireless network."
    ::= { hh3cDot11GlobeConfigGroup 1 }

hh3cDot11StaKeepALiveTimerIntvl OBJECT-TYPE
    SYNTAX      Unsigned32
    UNITS       "second"
    MAX-ACCESS  read-write
    STATUS      current
    DESCRIPTION
        "Represents the interval of the keep alive requests sent between
        AP and STA."
    ::= { hh3cDot11GlobeConfigGroup 2 }

hh3cDot11StaIdleTimerIntvl OBJECT-TYPE
    SYNTAX      Integer32
    UNITS       "second"
    MAX-ACCESS  read-write
    STATUS      current
    DESCRIPTION
        "Represents the interval for which the link between AP and STA
        ( power-save or awake ) can be idle."
    ::= { hh3cDot11GlobeConfigGroup 3 }

hh3cDot11BroadcastProbeReply OBJECT-TYPE
    SYNTAX      TruthValue
    MAX-ACCESS  read-write
    STATUS      current
    DESCRIPTION
        "Represents enable the AP to reply broadcast probe or not.
        'true' : The AP to reply broadcast probe is enabled.
        'false': The AP to reply broadcast probe is disabled"
    DEFVAL      { true }
    ::= { hh3cDot11GlobeConfigGroup 4 }

hh3cDot11APScanMode OBJECT-TYPE
    SYNTAX      INTEGER
        {
            active(1),
            passive(2)
        }
    MAX-ACCESS  read-write
    STATUS      current
    DESCRIPTION
        "Represents the scanning mode for AP.
        The following values are supported:
        active(1),  - AP will actively do scan.
        passive(2)  - AP will passively do scan."
    DEFVAL      { active }
    ::= { hh3cDot11GlobeConfigGroup 5 }

hh3cDot11ACCtrlTunnelSecSupport OBJECT-TYPE
    SYNTAX      Hh3cDot11TunnelSecSchemType
    MAX-ACCESS  read-write
    STATUS      current
    DESCRIPTION
        "Represents what security schemes are supported for CAPWAP Control
        tunnel."
    ::= { hh3cDot11GlobeConfigGroup 6 }

hh3cDot11ACDataTunnelSecSupport OBJECT-TYPE
    SYNTAX      Hh3cDot11TunnelSecSchemType
    MAX-ACCESS  read-write
    STATUS      current
    DESCRIPTION
        "Represents what security schemes are supported for CAPWAP data
        tunnel. The cleartxt is the default scheme."
    DEFVAL      { cleartxt }
    ::= { hh3cDot11GlobeConfigGroup 7 }

hh3cDot11ACAutoAPSupport OBJECT-TYPE
    SYNTAX      TruthValue
    MAX-ACCESS  read-write
    STATUS      current
    DESCRIPTION
        "Represents enable the auto AP functionality or not.
        'true' : The auto AP functionality is enabled.
        'false': The auto AP functionality is disabled"
    DEFVAL      { false }
    ::= { hh3cDot11GlobeConfigGroup 8 }

hh3cDot11AutoAPName OBJECT-TYPE
    SYNTAX      OCTET STRING(SIZE(0..127))
    MAX-ACCESS  read-write
    STATUS      current
    DESCRIPTION
        "Represents the name of auto AP which need to be made persistent.
        When read the value from the node, NULL value be returned."
    ::= { hh3cDot11GlobeConfigGroup 9 }

hh3cDot11PersistentName OBJECT-TYPE
    SYNTAX      OCTET STRING(SIZE(0..127))
    MAX-ACCESS  read-write
    STATUS      current
    DESCRIPTION
        "Represents the new name of auto AP after being made persistent.
        When read the value from the node, NULL value be returned."
    ::= { hh3cDot11GlobeConfigGroup 10 }

-- *****************************************************************************
-- * End of hh3cDot11GlobeConfigGroup Definition
-- *****************************************************************************

-- *****************************************************************************
-- *  hh3cDot11RadioPolicyTable Definition
-- *****************************************************************************
hh3cDot11RadioPolicyTable OBJECT-TYPE
    SYNTAX      SEQUENCE OF Hh3cDot11RadioPolicyEntry
    MAX-ACCESS  not-accessible
    STATUS      current
    DESCRIPTION
        "The table defines the parameters for radio policy, as per
        radio policy of CLI.
        One radio policy could be assigned to the different radios (AP)."
    ::= { hh3cDot11PolicyConfigGroup 1 }

hh3cDot11RadioPolicyEntry OBJECT-TYPE
    SYNTAX      Hh3cDot11RadioPolicyEntry
    MAX-ACCESS  not-accessible
    STATUS      current
    DESCRIPTION
        "Each entry contains information of each radio policy."
    INDEX
        {
            IMPLIED hh3cDot11RadioPolicyName
        }
    ::= { hh3cDot11RadioPolicyTable 1 }

Hh3cDot11RadioPolicyEntry ::= SEQUENCE
    {
        hh3cDot11RadioPolicyName        OCTET STRING,
        hh3cDot11BeaconInterval         Integer32,
        hh3cDot11DtimInterval           Integer32,
        hh3cDot11RtsThreshold           Integer32,
        hh3cDot11FragThreshold          Integer32,
        hh3cDot11ShortRetryThreshold    Integer32,
        hh3cDot11LongRetryThreshold     Integer32,
        hh3cDot11MaxRxLifetime          Unsigned32,
        hh3cDot11RdoPolicyRowStatus     RowStatus,
        hh3cDot11RdoClientMaxCount      Integer32
    }

hh3cDot11RadioPolicyName OBJECT-TYPE
    SYNTAX      OCTET STRING(SIZE(0..127))
    MAX-ACCESS  not-accessible
    STATUS      current
    DESCRIPTION
        "Represents the name of radio policy."
    ::= { hh3cDot11RadioPolicyEntry 1 }

hh3cDot11BeaconInterval OBJECT-TYPE
    SYNTAX      Integer32
    UNITS       "millisecond"
    MAX-ACCESS  read-create
    STATUS      current
    DESCRIPTION
        "Represents the interval for Beacon management frame."
    DEFVAL      { 100 }
    ::= { hh3cDot11RadioPolicyEntry 2 }

hh3cDot11DtimInterval OBJECT-TYPE
    SYNTAX      Integer32
    MAX-ACCESS  read-create
    STATUS      current
    DESCRIPTION
        "Represents the number of beacon intervals that shall elapse
        between transmission of Beacons frames containing a Traffic
        Indication Map (TIM) element whose DTIM Count field is 0.
        This value is transmitted in the Delivery TIM (DTIM) Period
        field of Beacon frames."
    DEFVAL      { 1 }
    ::= { hh3cDot11RadioPolicyEntry 3 }

hh3cDot11RtsThreshold OBJECT-TYPE
    SYNTAX      Integer32
    UNITS       "byte"
    MAX-ACCESS  read-create
    STATUS      current
    DESCRIPTION
        "Represents the current minimum size,in octets,of the MAC
        protocol data unit (MPDU), below which a Request to send/Clear
        to send (RTS/CTS) handshake shall not be performed."
    DEFVAL      { 2346 }
    ::= { hh3cDot11RadioPolicyEntry 4 }

hh3cDot11FragThreshold OBJECT-TYPE
    SYNTAX      Integer32
    UNITS       "byte"
    MAX-ACCESS  read-create
    STATUS      current
    DESCRIPTION
        "Represents the current maximum size, in octets, of the MPDU that
        may be delivered to the PHY. A MSDU shall be broken into
        fragments if its size exceeds the value of this attribute after
        adding MAC headers and trailers."
    DEFVAL      { 2346 }
    ::= { hh3cDot11RadioPolicyEntry 5 }

hh3cDot11ShortRetryThreshold OBJECT-TYPE
    SYNTAX      Integer32
    MAX-ACCESS  read-create
    STATUS      current
    DESCRIPTION
        "Represents the maximum number of transmission attempts of a
        frame, the length of which is less than or equal to
        hh3cDot11RTSThreshold, that shall be made before a failure
        condition is indicated."
    DEFVAL      { 7 }
    ::= { hh3cDot11RadioPolicyEntry 6 }

hh3cDot11LongRetryThreshold OBJECT-TYPE
    SYNTAX      Integer32
    MAX-ACCESS  read-create
    STATUS      current
    DESCRIPTION
        "Represents the maximum number of transmission attempts of a
        frame, the length of which is longer than hh3cDot11RTSThreshold,
        that shall be made before a failure condition is indicated."
    DEFVAL      { 4 }
    ::= { hh3cDot11RadioPolicyEntry 7 }

hh3cDot11MaxRxLifetime OBJECT-TYPE
    SYNTAX      Unsigned32
    UNITS       "millisecond"
    MAX-ACCESS  read-create
    STATUS      current
    DESCRIPTION
        "Represents the elapsed time in TU. After the time specified by
        hh3cDot11MaxRxLifetime, the further attempts to reassemble the
        MSDU shall be terminated."
    DEFVAL      { 2000 }
    ::= { hh3cDot11RadioPolicyEntry 8 }

hh3cDot11RdoPolicyRowStatus OBJECT-TYPE
    SYNTAX      RowStatus
    MAX-ACCESS  read-create
    STATUS      current
    DESCRIPTION
        "The status of this table entry."
    ::= { hh3cDot11RadioPolicyEntry 9 }

hh3cDot11RdoClientMaxCount OBJECT-TYPE
    SYNTAX      Integer32(0..2147483647)
    MAX-ACCESS  read-create
    STATUS      current
    DESCRIPTION
        "Represent the maximum number of stations supported by
        this radio policy."
    ::= { hh3cDot11RadioPolicyEntry 10 }
-- *****************************************************************************
-- * End of hh3cDot11RadioPolicyTable Definition
-- *****************************************************************************

-- *****************************************************************************
-- *  hh3cDot11ServicePolicyTable Definition
-- *****************************************************************************
hh3cDot11ServicePolicyTable OBJECT-TYPE
    SYNTAX      SEQUENCE OF Hh3cDot11ServicePolicyEntry
    MAX-ACCESS  not-accessible
    STATUS      current
    DESCRIPTION
        "The table defines the parameters for ESS, as per service policy
        of CLI.
        One service policy could be assigned to the different radios
        (AP)."
    ::= { hh3cDot11PolicyConfigGroup 2 }

hh3cDot11ServicePolicyEntry OBJECT-TYPE
    SYNTAX      Hh3cDot11ServicePolicyEntry
    MAX-ACCESS  not-accessible
    STATUS      current
    DESCRIPTION
        "Each entry contains information of each service policy."
    INDEX
        {
            hh3cDot11ServicePolicyID
        }
    ::= { hh3cDot11ServicePolicyTable 1 }

Hh3cDot11ServicePolicyEntry ::= SEQUENCE
    {
        hh3cDot11ServicePolicyID       Hh3cDot11ServicePolicyIDType,
        hh3cDot11SSIDName              Hh3cDot11SSIDStringType,
        hh3cDot11SSIDHidden            TruthValue,
        hh3cDot11AuthenMode            Hh3cDot11AuthenType,
        hh3cDot11SSIDEncryptionMode    Hh3cDot11SSIDEncryptModeType,
        hh3cDot11WlanInfBindingType    OCTET STRING,
        hh3cDot11WlanInfBindingID      Integer32,
        hh3cDot11SrvPolicyRowStatus    RowStatus,
        hh3cDot11ClientMaxCount        Integer32
    }

hh3cDot11ServicePolicyID OBJECT-TYPE
    SYNTAX      Hh3cDot11ServicePolicyIDType
    MAX-ACCESS  not-accessible
    STATUS      current
    DESCRIPTION
        "Represents the ID of each service policy."
    ::= { hh3cDot11ServicePolicyEntry 1 }

hh3cDot11SSIDName OBJECT-TYPE
    SYNTAX      Hh3cDot11SSIDStringType
    MAX-ACCESS  read-create
    STATUS      current
    DESCRIPTION
        "Represents the ESS. As per CLI, the value of
        service policy name will be SSID."
    ::= { hh3cDot11ServicePolicyEntry 2 }

hh3cDot11SSIDHidden OBJECT-TYPE
    SYNTAX      TruthValue
    MAX-ACCESS  read-create
    STATUS      current
    DESCRIPTION
        "This attribute controls whether the SSID will be advertised in
        the beacon frame.
        If it is true, then SSID will not be advertised in the beacon
        frame."
    DEFVAL      { false }
    ::= { hh3cDot11ServicePolicyEntry 3 }

hh3cDot11AuthenMode OBJECT-TYPE
    SYNTAX      Hh3cDot11AuthenType
    MAX-ACCESS  read-create
    STATUS      current
    DESCRIPTION
        "Represents the Authentication mode defined by 802.11."
    ::= { hh3cDot11ServicePolicyEntry 4 }

hh3cDot11SSIDEncryptionMode OBJECT-TYPE
    SYNTAX      Hh3cDot11SSIDEncryptModeType
    MAX-ACCESS  read-create
    STATUS      current
    DESCRIPTION
        "Represents the encryption mode for this ESS."
    DEFVAL      { cipher }
    ::= { hh3cDot11ServicePolicyEntry 5 }

hh3cDot11WlanInfBindingType OBJECT-TYPE
    SYNTAX      OCTET STRING
    MAX-ACCESS  read-create
    STATUS      current
    DESCRIPTION
        "Represents the service policy will bind to what kind of
        data forwarding interface."
    DEFVAL      { "WLAN-ESS" }
    ::= { hh3cDot11ServicePolicyEntry 6 }

hh3cDot11WlanInfBindingID OBJECT-TYPE
    SYNTAX      Integer32
    MAX-ACCESS  read-create
    STATUS      current
    DESCRIPTION
        "Represents the interface ID of the interface that ESS will
        bind to.
        If the value is set to -1, the binding will be removed."
    ::= { hh3cDot11ServicePolicyEntry 7 }

hh3cDot11SrvPolicyRowStatus OBJECT-TYPE
    SYNTAX      RowStatus
    MAX-ACCESS  read-create
    STATUS      current
    DESCRIPTION
        "The status of this table entry."
    ::= { hh3cDot11ServicePolicyEntry 8 }

hh3cDot11ClientMaxCount OBJECT-TYPE
    SYNTAX      Integer32(0..2147483647)
    MAX-ACCESS  read-create
    STATUS      current
    DESCRIPTION
        "Represent the maximum number of stations supported by
        this service policy."
    ::= { hh3cDot11ServicePolicyEntry 9 }
-- *****************************************************************************
-- * End of hh3cDot11ServicePolicyTable Definition
-- *****************************************************************************

-- *****************************************************************************
-- *  hh3cDot11ServicePolicyExtTable Definition
-- *****************************************************************************
hh3cDot11ServicePolicyExtTable OBJECT-TYPE
    SYNTAX      SEQUENCE OF Hh3cDot11ServicePolicyExtEntry
    MAX-ACCESS  not-accessible
    STATUS      current
    DESCRIPTION
        "The table defines the parameters for ESS, as per service policy
        of CLI.
        When the value of hh3cDot11SSIDEncryptionMode equals to cipher(2),
        more configuration for a ESS will be put into the table."
    ::= { hh3cDot11PolicyConfigGroup 3 }

hh3cDot11ServicePolicyExtEntry OBJECT-TYPE
    SYNTAX      Hh3cDot11ServicePolicyExtEntry
    MAX-ACCESS  not-accessible
    STATUS      current
    DESCRIPTION
        "Each entry contains information of each service policy under cipher(2)
        mode."
    INDEX
        {
            hh3cDot11ServicePolicyExtID
        }
    ::= { hh3cDot11ServicePolicyExtTable 1 }

Hh3cDot11ServicePolicyExtEntry ::= SEQUENCE
    {
        hh3cDot11ServicePolicyExtID       Hh3cDot11ServicePolicyIDType,
        hh3cDot11SecIEStatus              Hh3cDot11SecIEStatusType,
        hh3cDot11SecurityCiphers          INTEGER,
        hh3cDot11CipherKeyIndex           INTEGER,
        hh3cDot11CipherKey                OCTET STRING,
        hh3cDot11SrvPolicyExtRowStatus    RowStatus
    }

hh3cDot11ServicePolicyExtID OBJECT-TYPE
    SYNTAX      Hh3cDot11ServicePolicyIDType
    MAX-ACCESS  not-accessible
    STATUS      current
    DESCRIPTION
        "Represents the ID of each service policy."
    ::= { hh3cDot11ServicePolicyExtEntry 1 }

hh3cDot11SecIEStatus OBJECT-TYPE
    SYNTAX      Hh3cDot11SecIEStatusType
    MAX-ACCESS  read-create
    STATUS      current
    DESCRIPTION
        "To enable the security Information element in the beacon and
        probe response frames sent by AP."
    ::= { hh3cDot11ServicePolicyExtEntry 2 }

hh3cDot11SecurityCiphers OBJECT-TYPE
    SYNTAX      INTEGER
    MAX-ACCESS  read-create
    STATUS      current
    DESCRIPTION
        "The WLAN system support the following cipher type for data frame
        encryption.
        wep40(2)
        tkip(4)
        aesccmp(16)
        wep104(32)
        For each service policy,it could support multiple cipher types at
        the same time.So the value of object could combine multiple value
        of cipher type above.
        When the value of node equals to zero, it means no configuration or
        undo operation."
    ::= { hh3cDot11ServicePolicyExtEntry 3 }

hh3cDot11CipherKeyIndex OBJECT-TYPE
    SYNTAX      INTEGER
    MAX-ACCESS  read-create
    STATUS      current
    DESCRIPTION
        "Represents the key index of cipher key for packet.
        When hh3cDot11SecurityCiphers value is wep40 or wep104,
        the configuration will take effective."
    DEFVAL      { 1 }
    ::= { hh3cDot11ServicePolicyExtEntry 4 }

hh3cDot11CipherKey OBJECT-TYPE
    SYNTAX      OCTET STRING
    MAX-ACCESS  read-create
    STATUS      current
    DESCRIPTION
        "Represents the cipher key for packet.
        When hh3cDot11SecurityCiphers value is wep40 or wep104,
        the configuration will take effective."
    ::= { hh3cDot11ServicePolicyExtEntry 5 }

hh3cDot11SrvPolicyExtRowStatus OBJECT-TYPE
    SYNTAX      RowStatus
    MAX-ACCESS  read-create
    STATUS      current
    DESCRIPTION
        "The status of this table entry."
    ::= { hh3cDot11ServicePolicyExtEntry 6 }
-- *****************************************************************************
-- * End of hh3cDot11ServicePolicyExtTable Definition
-- *****************************************************************************

-- *****************************************************************************
-- *  hh3cDot11APTemplateTable Definition
-- *****************************************************************************
hh3cDot11APTemplateTable OBJECT-TYPE
    SYNTAX      SEQUENCE OF Hh3cDot11APTemplateEntry
    MAX-ACCESS  not-accessible
    STATUS      current
    DESCRIPTION
        "By AP template CLI, administrator will configure the parameters of AP
        by convenience.
        Before AP boot up and connect to AC by CAPWAP tunnel, administrator
        will create AP template for each AP. When AP connect to AC,
        AC will assign configuration to AP by hh3cDot11APSerialID
        information in AP template."
    ::= { hh3cDot11APConfigGroup 1 }

hh3cDot11APTemplateEntry OBJECT-TYPE
    SYNTAX      Hh3cDot11APTemplateEntry
    MAX-ACCESS  not-accessible
    STATUS      current
    DESCRIPTION
        "Each entry contains configuration information for each AP."
    INDEX
        {
            hh3cDot11APTemplateName
        }
    ::= { hh3cDot11APTemplateTable 1 }

Hh3cDot11APTemplateEntry ::= SEQUENCE
    {
        hh3cDot11APTemplateName             OCTET STRING,
        hh3cDot11APSerialID                 OCTET STRING,
        hh3cDot11TemplateAPModelAlias       OCTET STRING,
        hh3cDot11Description                OCTET STRING,
        hh3cDot11APWorkMode                 INTEGER,
        hh3cDot11APTemplateRowStatus        RowStatus,
        hh3cDot11APName                     OCTET STRING,
        hh3cDot11StatisInterv               Integer32,
        hh3cDot11APBroadcastProbeReply      TruthValue,
        hh3cDot11StaIdleTimerInterv         Integer32,
        hh3cDot11StaKeepAliveTimerInterv    Integer32,
        hh3cDot11APCir                      Integer32,
        hh3cDot11APCbs                      Integer32
    }

hh3cDot11APTemplateName OBJECT-TYPE
    SYNTAX      OCTET STRING(SIZE(0..127))
    MAX-ACCESS  not-accessible
    STATUS      current
    DESCRIPTION
        "Represents the name of AP template."
    ::= { hh3cDot11APTemplateEntry 1 }

hh3cDot11APSerialID OBJECT-TYPE
    SYNTAX      OCTET STRING
    MAX-ACCESS  read-create
    STATUS      current
    DESCRIPTION
        "Represents AP serial id."
    ::= { hh3cDot11APTemplateEntry 2 }

hh3cDot11TemplateAPModelAlias OBJECT-TYPE
    SYNTAX      OCTET STRING
    MAX-ACCESS  read-create
    STATUS      current
    DESCRIPTION
        "Represents the alias of AP model name."
    ::= { hh3cDot11APTemplateEntry 3 }

hh3cDot11Description OBJECT-TYPE
    SYNTAX      OCTET STRING
    MAX-ACCESS  read-create
    STATUS      current
    DESCRIPTION
        "This attribute will give more information about AP.
        Administrator could suggest the location, owner or
        other information for each AP.
        If the value is set to NULL, the description will be removed."
    ::= { hh3cDot11APTemplateEntry 4 }

hh3cDot11APWorkMode OBJECT-TYPE
    SYNTAX      INTEGER
        {
            normal(1),
            monitor(2)
        }
    MAX-ACCESS  read-create
    STATUS      current
    DESCRIPTION
        "Represents what work mode for AP.
        The following values are supported:
        normal(1),  - AP will supply WLAN service.
        monitor(2)  - AP will be a monitor to find attack."
    DEFVAL      { normal }
    ::= { hh3cDot11APTemplateEntry 5 }

hh3cDot11APTemplateRowStatus OBJECT-TYPE
    SYNTAX      RowStatus
    MAX-ACCESS  read-create
    STATUS      current
    DESCRIPTION
        "The status of this table entry."
    ::= { hh3cDot11APTemplateEntry 6 }

hh3cDot11APName OBJECT-TYPE
    SYNTAX      OCTET STRING(SIZE(0..15))
    MAX-ACCESS  read-create
    STATUS      current
    DESCRIPTION
        "Represents the AP name."
    ::= { hh3cDot11APTemplateEntry 7 }

hh3cDot11StatisInterv OBJECT-TYPE
    SYNTAX      Integer32
    UNITS       "second"
    MAX-ACCESS  read-create
    STATUS      current
    DESCRIPTION
        "Represents the interval of radio statistic."
    ::= { hh3cDot11APTemplateEntry 8 }

hh3cDot11APBroadcastProbeReply OBJECT-TYPE
    SYNTAX      TruthValue
    MAX-ACCESS  read-create
    STATUS      current
    DESCRIPTION
        "Represents enable the AP to reply broadcast probe or not.
        'true' : The AP to reply broadcast probe is enabled.
        'false': The AP to reply broadcast probe is disabled"
    DEFVAL      { true }
    ::= { hh3cDot11APTemplateEntry 9 }

hh3cDot11StaIdleTimerInterv OBJECT-TYPE
    SYNTAX      Integer32
    UNITS       "second"
    MAX-ACCESS  read-create
    STATUS      current
    DESCRIPTION
        "Represents the interval for which the link between AP and STA
        ( power-save or awake ) can be idle."
    ::= { hh3cDot11APTemplateEntry 10 }

hh3cDot11StaKeepAliveTimerInterv OBJECT-TYPE
    SYNTAX      Integer32
    UNITS       "second"
    MAX-ACCESS  read-create
    STATUS      current
    DESCRIPTION
        "Represents the interval of the keep alive requests sent between
        AP and STA."
    ::= { hh3cDot11APTemplateEntry 11 }

hh3cDot11APCir OBJECT-TYPE
    SYNTAX      Integer32
    UNITS       "Kbps"
    MAX-ACCESS  read-create
    STATUS      current
    DESCRIPTION
        "Represents the committed information rate between AP and AC."
    ::= { hh3cDot11APTemplateEntry 12 }

hh3cDot11APCbs OBJECT-TYPE
    SYNTAX      Integer32
    UNITS       "Bytes"
    MAX-ACCESS  read-create
    STATUS      current
    DESCRIPTION
        "Represents the committed burst size between AP and AC."
    ::= { hh3cDot11APTemplateEntry 13 }
-- *****************************************************************************
-- *  End of  hh3cDot11APTemplateTable Definition
-- *****************************************************************************

-- *****************************************************************************
-- *  hh3cDot11RadioToConfigTable Definition
-- *****************************************************************************
hh3cDot11RadioToConfigTable OBJECT-TYPE
    SYNTAX      SEQUENCE OF Hh3cDot11RadioToConfigEntry
    MAX-ACCESS  not-accessible
    STATUS      current
    DESCRIPTION
        "Before AP connects to AC, administrator will configure radio
        parameter to each radio."
    ::= { hh3cDot11APConfigGroup 2 }

hh3cDot11RadioToConfigEntry OBJECT-TYPE
    SYNTAX      Hh3cDot11RadioToConfigEntry
    MAX-ACCESS  not-accessible
    STATUS      current
    DESCRIPTION
        "Each entry contains configuration information for each radio."
    INDEX
        {
            hh3cDot11APTemplateNameCfg,
            hh3cDot11CfgRadioID
        }
    ::= { hh3cDot11RadioToConfigTable 1 }

Hh3cDot11RadioToConfigEntry ::= SEQUENCE
    {
        hh3cDot11APTemplateNameCfg     OCTET STRING,
        hh3cDot11CfgRadioID            Hh3cDot11RadioScopeType,
        hh3cDot11CfgRadioPolicyName    OCTET STRING,
        hh3cDot11CfgRadioType          Hh3cDot11RadioType,
        hh3cDot11CfgChannel            Hh3cDot11ChannelScopeType,
        hh3cDot11CfgMaxTxPowerLevel    Hh3cDot11TxPwrLevelScopeType,
        hh3cDot11PreambleLen           Hh3cDot11PreambleType,
        hh3cDot11CfgRadioStatus        TruthValue
    }

hh3cDot11APTemplateNameCfg OBJECT-TYPE
    SYNTAX      OCTET STRING(SIZE(0..127))
    MAX-ACCESS  not-accessible
    STATUS      current
    DESCRIPTION
        "Represents the name of AP template."
    ::= { hh3cDot11RadioToConfigEntry 1 }

hh3cDot11CfgRadioID OBJECT-TYPE
    SYNTAX      Hh3cDot11RadioScopeType
    MAX-ACCESS  not-accessible
    STATUS      current
    DESCRIPTION
        "Represents each radio."
    ::= { hh3cDot11RadioToConfigEntry 2 }

hh3cDot11CfgRadioPolicyName OBJECT-TYPE
    SYNTAX      OCTET STRING
    MAX-ACCESS  read-create
    STATUS      current
    DESCRIPTION
        "Represents the name of radio policy."
    ::= { hh3cDot11RadioToConfigEntry 3 }

hh3cDot11CfgRadioType OBJECT-TYPE
    SYNTAX      Hh3cDot11RadioType
    MAX-ACCESS  read-create
    STATUS      current
    DESCRIPTION
        "Represents the radio will work with which 802.11 radio type."
    ::= { hh3cDot11RadioToConfigEntry 4 }

hh3cDot11CfgChannel OBJECT-TYPE
    SYNTAX      Hh3cDot11ChannelScopeType
    MAX-ACCESS  read-create
    STATUS      current
    DESCRIPTION
        "Represents the channel allocation of radio."
    ::= { hh3cDot11RadioToConfigEntry 5 }

hh3cDot11CfgMaxTxPowerLevel OBJECT-TYPE
    SYNTAX      Hh3cDot11TxPwrLevelScopeType
    UNITS       "dbm"
    MAX-ACCESS  read-create
    STATUS      current
    DESCRIPTION
        "Represents the maximal transmit power scope for AP."
    ::= { hh3cDot11RadioToConfigEntry 6 }

hh3cDot11PreambleLen OBJECT-TYPE
    SYNTAX      Hh3cDot11PreambleType
    MAX-ACCESS  read-create
    STATUS      current
    DESCRIPTION
        "Represents whether use long or short preamble for 802.11 MAC
        frame.
        When hh3cDot11CfgRadioType is either dot11b or dot11g,
        then value for hh3cDot11PreambleLen will be valid.
        Othwise, the value for it will be invalid."
    DEFVAL      { short }
    ::= { hh3cDot11RadioToConfigEntry 7 }

hh3cDot11CfgRadioStatus OBJECT-TYPE
    SYNTAX      TruthValue
    MAX-ACCESS  read-create
    STATUS      current
    DESCRIPTION
        "Represents the radio admin status whether is enabled
        or disabled."
    ::= { hh3cDot11RadioToConfigEntry 8 }
-- *****************************************************************************
-- *  End of  hh3cDot11RadioToConfigTable Definition
-- *****************************************************************************

-- *****************************************************************************
-- *  hh3cDot11APServiceSetTable Definition
-- *****************************************************************************
hh3cDot11APServiceSetTable OBJECT-TYPE
    SYNTAX      SEQUENCE OF Hh3cDot11APServiceSetEntry
    MAX-ACCESS  not-accessible
    STATUS      current
    DESCRIPTION
        "For each radio, it could configure multiple service policies.
        The table describes the relationship between radio and
        service policies."
    ::= { hh3cDot11APConfigGroup 3 }

hh3cDot11APServiceSetEntry OBJECT-TYPE
    SYNTAX      Hh3cDot11APServiceSetEntry
    MAX-ACCESS  not-accessible
    STATUS      current
    DESCRIPTION
        "Each entry contains service policy information for each
        specific radio of AP."
    INDEX
        {
            hh3cDot11APTemplateNameCfg,
            hh3cDot11CfgRadioID,
            hh3cDot11CfgServicePolicyID
        }
    ::= { hh3cDot11APServiceSetTable 1 }

Hh3cDot11APServiceSetEntry ::= SEQUENCE
    {
        hh3cDot11CfgServicePolicyID    Hh3cDot11ServicePolicyIDType,
        hh3cDot11SrvSetRowStatus       RowStatus
    }

hh3cDot11CfgServicePolicyID OBJECT-TYPE
    SYNTAX      Hh3cDot11ServicePolicyIDType
    MAX-ACCESS  not-accessible
    STATUS      current
    DESCRIPTION
        "Represents the ID of each service policy used by the AP."
    ::= { hh3cDot11APServiceSetEntry 1 }

hh3cDot11SrvSetRowStatus OBJECT-TYPE
    SYNTAX      RowStatus
    MAX-ACCESS  read-create
    STATUS      current
    DESCRIPTION
        "The status of this table entry."
    ::= { hh3cDot11APServiceSetEntry 2 }
-- *****************************************************************************
-- * End of hh3cDot11APServiceSetTable Definition
-- *****************************************************************************

-- *****************************************************************************
-- *  hh3cDot11RadioIntfConfigTable Definition
-- *****************************************************************************
hh3cDot11RadioIntfConfigTable OBJECT-TYPE
    SYNTAX      SEQUENCE OF Hh3cDot11RadioIntfConfigEntry
    MAX-ACCESS  not-accessible
    STATUS      current
    DESCRIPTION
        "The table defines the parameters for radio in AP, as per
        radio."
    ::= { hh3cDot11RadioIntfConfigGroup 1 }

hh3cDot11RadioIntfConfigEntry OBJECT-TYPE
    SYNTAX      Hh3cDot11RadioIntfConfigEntry
    MAX-ACCESS  not-accessible
    STATUS      current
    DESCRIPTION
        "Each entry contains information of each radio in AP."
    INDEX
        {
            hh3cDot11RadioIfIdx
        }
    ::= { hh3cDot11RadioIntfConfigTable 1 }

Hh3cDot11RadioIntfConfigEntry ::= SEQUENCE
    {
        hh3cDot11RadioIfIdx               Integer32,
        hh3cDot11RadioCfgBeaconIntvl      Integer32,
        hh3cDot11RadioCfgDtimIntvl        Integer32,
        hh3cDot11RadioCfgRtsThreshold     Integer32,
        hh3cDot11RadioCfgFragThreshold    Integer32,
        hh3cDot11RadioCfgShtRetryThld     Integer32,
        hh3cDot11RadioCfglongRtrThld      Integer32,
        hh3cDot11RadioCfgMaxRxLifetime    Unsigned32,
        hh3cDot11RadioCfgType             Hh3cDot11RadioType,
        hh3cDot11RadioCfgChannel          Hh3cDot11ChannelScopeType,
        hh3cDot11RadioCfgMaxTxPwrLvl      Hh3cDot11TxPwrLevelScopeType,
        hh3cDot11RadioCfgPreambleLen      Hh3cDot11PreambleType
    }

hh3cDot11RadioIfIdx OBJECT-TYPE
    SYNTAX      Integer32
    MAX-ACCESS  not-accessible
    STATUS      current
    DESCRIPTION
        "Represents the Radio IfIndex of radio in AP."
    ::= { hh3cDot11RadioIntfConfigEntry 1 }

hh3cDot11RadioCfgBeaconIntvl OBJECT-TYPE
    SYNTAX      Integer32
    UNITS       "millisecond"
    MAX-ACCESS  read-write
    STATUS      current
    DESCRIPTION
        "Represents the interval for Beacon management frame."
    DEFVAL { 100 }
    ::= { hh3cDot11RadioIntfConfigEntry 2 }

hh3cDot11RadioCfgDtimIntvl OBJECT-TYPE
    SYNTAX      Integer32
    MAX-ACCESS  read-write
    STATUS      current
    DESCRIPTION
        "Represents the number of beacon intervals that shall elapse
        between transmission of Beacons frames containing a Traffic
        Indication Map (TIM) element whose DTIM Count field is 0.
        This value is transmitted in the Delivery TIM (DTIM) Period
        field of Beacon frames."
    DEFVAL { 1 }
    ::= { hh3cDot11RadioIntfConfigEntry 3 }

hh3cDot11RadioCfgRtsThreshold OBJECT-TYPE
    SYNTAX      Integer32
    UNITS       "Byte"
    MAX-ACCESS  read-write
    STATUS      current
    DESCRIPTION
        "Represents the current minimum size,in octets,of the MAC
        protocol data unit (MPDU), below which a Request to send/Clear
        to send (RTS/CTS) handshake shall not be performed."
    DEFVAL { 2346 }
    ::= { hh3cDot11RadioIntfConfigEntry 4 }

hh3cDot11RadioCfgFragThreshold OBJECT-TYPE
    SYNTAX      Integer32
    UNITS       "Byte"
    MAX-ACCESS  read-write
    STATUS      current
    DESCRIPTION
        "Represents the current maximum size, in octets, of the MPDU that
        may be delivered to the PHY. A MSDU shall be broken into
        fragments if its size exceeds the value of this attribute after
        adding MAC headers and trailers."
    DEFVAL { 2346 }
    ::= { hh3cDot11RadioIntfConfigEntry 5 }

hh3cDot11RadioCfgShtRetryThld OBJECT-TYPE
    SYNTAX      Integer32
    MAX-ACCESS  read-write
    STATUS      current
    DESCRIPTION
        "Represents the maximum number of transmission attempts of a
        frame, the length of which is less than or equal to
        hh3cDot11RadioRTSThreshold, that shall be made before a failure
        condition is indicated."
    DEFVAL { 5 }
    ::= { hh3cDot11RadioIntfConfigEntry 6 }

hh3cDot11RadioCfglongRtrThld OBJECT-TYPE
    SYNTAX      Integer32
    MAX-ACCESS  read-write
    STATUS      current
    DESCRIPTION
        "Represents the maximum number of transmission attempts of a
        frame, the length of which is longer than
        hh3cDot11RadioRTSThreshold, that shall be made before a
        failure condition is indicated."
    DEFVAL { 5 }
    ::= { hh3cDot11RadioIntfConfigEntry 7 }

hh3cDot11RadioCfgMaxRxLifetime OBJECT-TYPE
    SYNTAX      Unsigned32
    UNITS       "millisecond"
    MAX-ACCESS  read-write
    STATUS      current
    DESCRIPTION
        "Represents the elapsed time in TU. After the time specified by
        hh3cDot11RadioCfgMaxRxLifetime, the further attempts to reassemble
        the MSDU shall be terminated."
    DEFVAL { 2000 }
    ::= { hh3cDot11RadioIntfConfigEntry 8 }

hh3cDot11RadioCfgType OBJECT-TYPE
    SYNTAX      Hh3cDot11RadioType
    MAX-ACCESS  read-write
    STATUS      current
    DESCRIPTION
        "Represents the radio will work with which 802.11 radio type."
    ::= { hh3cDot11RadioIntfConfigEntry 9 }

hh3cDot11RadioCfgChannel OBJECT-TYPE
    SYNTAX      Hh3cDot11ChannelScopeType
    MAX-ACCESS  read-write
    STATUS      current
    DESCRIPTION
        "Represents the channel allocation of radio."
    DEFVAL { 1 }
    ::= { hh3cDot11RadioIntfConfigEntry 10 }

hh3cDot11RadioCfgMaxTxPwrLvl OBJECT-TYPE
    SYNTAX      Hh3cDot11TxPwrLevelScopeType
    UNITS       "dbm"
    MAX-ACCESS  read-write
    STATUS      current
    DESCRIPTION
        "Represents the maximal transmit power scope for AP."
    ::= { hh3cDot11RadioIntfConfigEntry 11 }

hh3cDot11RadioCfgPreambleLen OBJECT-TYPE
    SYNTAX      Hh3cDot11PreambleType
    MAX-ACCESS  read-write
    STATUS      current
    DESCRIPTION
        "Represents whether use long or short preamble for 802.11 MAC
        frame."
    DEFVAL { short }
    ::= { hh3cDot11RadioIntfConfigEntry 12 }

-- *****************************************************************************
-- *  End of hh3cDot11RadioIntfConfigTable Definition
-- *****************************************************************************

-- *****************************************************************************
-- *  hh3cDot11RadioIntfBindTable Definition
-- *****************************************************************************
hh3cDot11RadioIntfBindTable OBJECT-TYPE
    SYNTAX      SEQUENCE OF Hh3cDot11RadioIntfBindEntry
    MAX-ACCESS  not-accessible
    STATUS      current
    DESCRIPTION
        "The table defines the binding information for each radio in AP.
        "
    ::= { hh3cDot11RadioIntfConfigGroup 2 }

hh3cDot11RadioIntfBindEntry OBJECT-TYPE
    SYNTAX      Hh3cDot11RadioIntfBindEntry
    MAX-ACCESS  not-accessible
    STATUS      current
    DESCRIPTION
        "Each entry contains the radio interface binding information
        in AP."
    INDEX
        {
            hh3cDot11RadioIfIdx,
            hh3cDot11RadioIntfBindSvcPlcyID
        }
    ::= { hh3cDot11RadioIntfBindTable 1 }

Hh3cDot11RadioIntfBindEntry ::= SEQUENCE
    {
        hh3cDot11RadioIntfBindSvcPlcyID    Hh3cDot11ServicePolicyIDType,
        hh3cDot11RadioIntfBindIfIdx        Unsigned32,
        hh3cDot11RadioIntfBindRowStatus    RowStatus
    }

hh3cDot11RadioIntfBindSvcPlcyID OBJECT-TYPE
    SYNTAX      Hh3cDot11ServicePolicyIDType
    MAX-ACCESS  not-accessible
    STATUS      current
    DESCRIPTION
        "Represents the ID of each service policy."
    ::= { hh3cDot11RadioIntfBindEntry 1 }

hh3cDot11RadioIntfBindIfIdx OBJECT-TYPE
    SYNTAX      Unsigned32
    MAX-ACCESS  read-create
    STATUS      current
    DESCRIPTION
        "Represents the Ifindex of interface which is binded to
        the radio."
    ::= { hh3cDot11RadioIntfBindEntry 2 }

hh3cDot11RadioIntfBindRowStatus OBJECT-TYPE
    SYNTAX      RowStatus
    MAX-ACCESS  read-create
    STATUS      current
    DESCRIPTION
        "The status of this table entry."
    ::= { hh3cDot11RadioIntfBindEntry 3 }
-- *****************************************************************************
-- *  End of hh3cDot11RadioIntfBindTable Definition
-- *****************************************************************************

-- *****************************************************************************
-- *  hh3cDot11DataRateConfigTable Definition
-- *****************************************************************************
hh3cDot11DataRateConfigTable OBJECT-TYPE
    SYNTAX      SEQUENCE OF Hh3cDot11DataRateConfigEntry
    MAX-ACCESS  not-accessible
    STATUS      current
    DESCRIPTION
        "Table will provide data rate configuration for a specific radio type."
    ::= { hh3cDot11DataRateConfigGroup 1 }

hh3cDot11DataRateConfigEntry OBJECT-TYPE
    SYNTAX      Hh3cDot11DataRateConfigEntry
    MAX-ACCESS  not-accessible
    STATUS      current
    DESCRIPTION
        "Each entry of the table will provide data rate configuration for a
        specific radio type."
    INDEX
        {
            hh3cDot11RadioTypeID
        }
    ::= { hh3cDot11DataRateConfigTable 1 }

Hh3cDot11DataRateConfigEntry ::= SEQUENCE
    {
        hh3cDot11RadioTypeID         Hh3cDot11RadioType,
        hh3cDot11SupportedRateSet    OCTET STRING,
        hh3cDot11MandatoryRateSet    OCTET STRING,
        hh3cDot11DisabledRateSet     OCTET STRING
    }

hh3cDot11RadioTypeID OBJECT-TYPE
    SYNTAX      Hh3cDot11RadioType
    MAX-ACCESS  not-accessible
    STATUS      current
    DESCRIPTION
        "Represents the radio type."
    ::= { hh3cDot11DataRateConfigEntry 1 }

hh3cDot11SupportedRateSet OBJECT-TYPE
    SYNTAX      OCTET STRING(SIZE(0..255))
    MAX-ACCESS  read-write
    STATUS      current
    DESCRIPTION
        "Represents the supported rate set of a particular radio type."
    ::= { hh3cDot11DataRateConfigEntry 2 }

hh3cDot11MandatoryRateSet OBJECT-TYPE
    SYNTAX      OCTET STRING(SIZE(0..255))
    MAX-ACCESS  read-write
    STATUS      current
    DESCRIPTION
        "Represents the mandatory rate set of a particular radio type."
    ::= { hh3cDot11DataRateConfigEntry 3 }

hh3cDot11DisabledRateSet OBJECT-TYPE
    SYNTAX      OCTET STRING(SIZE(0..255))
    MAX-ACCESS  read-write
    STATUS      current
    DESCRIPTION
        "Represents the disabled rate set of a particular radio type."
    ::= { hh3cDot11DataRateConfigEntry 4 }
-- *****************************************************************************
-- *  End of hh3cDot11DataRateConfigTable Definition
-- *****************************************************************************

-- *****************************************************************************
-- *  hh3cDot11WlanEssIfTable Definition
-- *************************************************************************

hh3cDot11WlanEssIfTable OBJECT-TYPE
    SYNTAX      SEQUENCE OF Hh3cDot11WlanEssIfEntry
    MAX-ACCESS  not-accessible
    STATUS      current
    DESCRIPTION
        "This table is used to configure WLAN ESS interface."
    ::= { hh3cDot11InterfaceConfigGroup 1 }

hh3cDot11WlanEssIfEntry OBJECT-TYPE
    SYNTAX      Hh3cDot11WlanEssIfEntry
    MAX-ACCESS  not-accessible
    STATUS      current
    DESCRIPTION
        "Each entry contains the WLAN ESS interface configuration."
    INDEX
        {
            hh3cDot11WlanEssIfNumber
        }
    ::= { hh3cDot11WlanEssIfTable 1 }

Hh3cDot11WlanEssIfEntry ::= SEQUENCE
    {
        hh3cDot11WlanEssIfNumber      Integer32,
        hh3cDot11WlanEssIfIndex       Integer32,
        hh3cDot11IWlanEssRowStatus    RowStatus
    }

hh3cDot11WlanEssIfNumber OBJECT-TYPE
    SYNTAX      Integer32
    MAX-ACCESS  not-accessible
    STATUS      current
    DESCRIPTION
        "This node represents the WLAN ESS interface number."
    ::= { hh3cDot11WlanEssIfEntry 1 }

hh3cDot11WlanEssIfIndex OBJECT-TYPE
    SYNTAX      Integer32
    MAX-ACCESS  read-only
    STATUS      current
    DESCRIPTION
        "This node represents the ifIndex of WLAN-ESS interface."
    ::= { hh3cDot11WlanEssIfEntry 2 }

hh3cDot11IWlanEssRowStatus OBJECT-TYPE
    SYNTAX      RowStatus
    MAX-ACCESS  read-create
    STATUS      current
    DESCRIPTION
        "This node represents the WLAN ESS interface row status."
    ::= { hh3cDot11WlanEssIfEntry 3 }

-- *****************************************************************************
-- *  End of hh3cDot11WlanEssIfTable  Definition
-- *****************************************************************************
-- *****************************************************************************
-- *  hh3cDot11WlanBssIfTable Definition
-- *************************************************************************

hh3cDot11WlanBssIfTable OBJECT-TYPE
    SYNTAX      SEQUENCE OF Hh3cDot11WlanBssIfEntry
    MAX-ACCESS  not-accessible
    STATUS      current
    DESCRIPTION
        "This table is used to configure WLAN BSS interface."
    ::= { hh3cDot11InterfaceConfigGroup 2 }

hh3cDot11WlanBssIfEntry OBJECT-TYPE
    SYNTAX      Hh3cDot11WlanBssIfEntry
    MAX-ACCESS  not-accessible
    STATUS      current
    DESCRIPTION
        "Each entry contains the WLAN BSS interface configuration."
    INDEX
        {
            hh3cDot11WlanBssIfNumber
        }
    ::= { hh3cDot11WlanBssIfTable 1 }

Hh3cDot11WlanBssIfEntry ::= SEQUENCE
    {
        hh3cDot11WlanBssIfNumber     Integer32,
        hh3cDot11WlanBssIfIndex      Integer32,
        hh3cDot11WlanBssRowStatus    RowStatus
    }

hh3cDot11WlanBssIfNumber OBJECT-TYPE
    SYNTAX      Integer32
    MAX-ACCESS  not-accessible
    STATUS      current
    DESCRIPTION
        "This node represents the WLAN BSS interface number."
    ::= { hh3cDot11WlanBssIfEntry 1 }

hh3cDot11WlanBssIfIndex OBJECT-TYPE
    SYNTAX      Integer32
    MAX-ACCESS  read-only
    STATUS      current
    DESCRIPTION
        "This node represents the ifIndex of WLAN-BSS interface."
    ::= { hh3cDot11WlanBssIfEntry 2 }

hh3cDot11WlanBssRowStatus OBJECT-TYPE
    SYNTAX      RowStatus
    MAX-ACCESS  read-create
    STATUS      current
    DESCRIPTION
        "This node represents the WLAN BSS interface row status."
    ::= { hh3cDot11WlanBssIfEntry 3 }

-- *****************************************************************************
-- *  End of hh3cDot11WlanBssIfTable Definition
-- *****************************************************************************
-- *****************************************************************************
-- *  hh3cDot11WLANEthernetIfTable Definition
-- *************************************************************************

hh3cDot11WLANEthernetIfTable OBJECT-TYPE
    SYNTAX      SEQUENCE OF Hh3cDot11WLANEthernetIfEntry
    MAX-ACCESS  not-accessible
    STATUS      current
    DESCRIPTION
        "This table is used to configure WLAN Ethernet interface."
    ::= { hh3cDot11InterfaceConfigGroup 3 }

hh3cDot11WLANEthernetIfEntry OBJECT-TYPE
    SYNTAX      Hh3cDot11WLANEthernetIfEntry
    MAX-ACCESS  not-accessible
    STATUS      current
    DESCRIPTION
        "Each entry contains the WLAN Ethernet interface configuration."
    INDEX
        {
            hh3cDot11WlanEthernetIfNumber
        }
    ::= { hh3cDot11WLANEthernetIfTable 1 }

Hh3cDot11WLANEthernetIfEntry ::= SEQUENCE
    {
        hh3cDot11WlanEthernetIfNumber     Integer32,
        hh3cDot11WLANEthernetIfIndex      Integer32,
        hh3cDot11WlanEthernetRowStatus    RowStatus
    }

hh3cDot11WlanEthernetIfNumber OBJECT-TYPE
    SYNTAX      Integer32
    MAX-ACCESS  not-accessible
    STATUS      current
    DESCRIPTION
        "This node represents the WLAN Ethernet interface number."
    ::= { hh3cDot11WLANEthernetIfEntry 1 }

hh3cDot11WLANEthernetIfIndex OBJECT-TYPE
    SYNTAX      Integer32
    MAX-ACCESS  read-only
    STATUS      current
    DESCRIPTION
        "This node represents the ifIndex of WLAN-Ethernet interface."
    ::= { hh3cDot11WLANEthernetIfEntry 2 }

hh3cDot11WlanEthernetRowStatus OBJECT-TYPE
    SYNTAX      RowStatus
    MAX-ACCESS  read-create
    STATUS      current
    DESCRIPTION
        "This node represents the Wlan Ethernet interface row status."
    ::= { hh3cDot11WLANEthernetIfEntry 3 }

-- *****************************************************************************
-- *  End of hh3cDot11DataRateConfigTable Definition
-- *****************************************************************************

END
