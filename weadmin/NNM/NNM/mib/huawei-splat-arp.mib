-- ==================================================================
-- Copyright (C) 2002 by  HUAWEI TECHNOLOGIES. All rights reserved.
-- 
-- Description:  HUAWEI Lan Switch mac management MIB
-- Reference:
-- ------------------------------------------------------------------
HUAWEI-LswARP-MIB DEFINITIONS ::= BEGIN
IMPORTS
   
    MODULE-IDENTITY,OBJECT-TYPE, OBJECT-IDENTITY   
        FROM SNMPv2-SMI   

    lswCommon 
        FROM HUAWEI-3COM-OID-MIB;


	 hwLswArpMib MODULE-IDENTITY
	        LAST-UPDATED "200106290000Z"
	        ORGANIZATION ""
	        CONTACT-INFO
	        ""
	        DESCRIPTION
	        ""
	        REVISION "200106290000Z"
	        DESCRIPTION
	        ""
	        ::= { lswCommon  4 }

    hwLswProxyArpObject OBJECT-IDENTITY
            STATUS current
            DESCRIPTION
                "Description."
            ::= { hwLswArpMib 1 }
    hwLswProxyArpEnableTable OBJECT-TYPE
		SYNTAX  SEQUENCE OF HwLswProxyArpEnableEntry
		MAX-ACCESS not-accessible
		STATUS   current
		DESCRIPTION "Contains information that if proxy ARP enabled for every VLAN interface. "
		::= { hwLswProxyArpObject 1 }

	 hwLswProxyArpEnableEntry OBJECT-TYPE
		SYNTAX  HwLswProxyArpEnableEntry
		MAX-ACCESS not-accessible
		STATUS current
		DESCRIPTION 
		  "Contains information that if proxy ARP enabled for VLAN interface."
		INDEX   { hwLswIfIndex }
		::= { hwLswProxyArpEnableTable 1}

	HwLswProxyArpEnableEntry ::=
	SEQUENCE {	
		hwLswIfIndex INTEGER ,
        hwLswProxyArpStatus  INTEGER
		}
		
	hwLswIfIndex OBJECT-TYPE
		SYNTAX  INTEGER
		MAX-ACCESS read-only
		STATUS current
		DESCRIPTION " Vlan interface index "
		::= { hwLswProxyArpEnableEntry 1 }				
	
    hwLswProxyArpStatus OBJECT-TYPE 
        SYNTAX INTEGER	
        {
            disabled(0),
            enabled(1)
        }
        MAX-ACCESS  read-write
        STATUS current 
        DESCRIPTION " Proxy ARP status for this VLAN interface."
        ::= { hwLswProxyArpEnableEntry 2 }
        
		
END
