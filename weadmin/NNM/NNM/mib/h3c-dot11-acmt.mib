-- =============================================================================
-- Copyright (C) 2006 by HUAWEI-3COM TECHNOLOGIES.  All rights reserved.
--
-- Description:
--   The file defines a MIB to provide wireless switch object and CAPWAP
--   tunnel information.
-- Reference:
-- =============================================================================
H3C-DOT11-ACMT-MIB DEFINITIONS ::= BEGIN

IMPORTS
        MODULE-IDENTITY,
        OBJECT-TYPE,
        NOTIFICATION-TYPE,
        Integer32,
        Counter32
    FROM SNMPv2-SMI
        h3cDot11,
        H3cDot11MACModeType,
        H3cDot11TunnelSecSchemType,
        H3cDot11ObjectIDType
    FROM H3C-DOT11-REF-MIB;

h3cDot11ACMT MODULE-IDENTITY
    LAST-UPDATED "200712211800Z"        -- Dec 21, 2007 at 18:00 GMT
    ORGANIZATION
        "Hangzhou H3C Technologies Co., Ltd."
    CONTACT-INFO
        "Platform Team Hangzhou H3C Technologies Co., Ltd.
         Hai-Dian District Beijing P.R. China
         Http://www.h3c.com
         Zip:100085"
    DESCRIPTION
        "This MIB defines information as per wireless AC and tunnel between
        AP and AC.
        If NMS intends to get more detailed information for the AP and AC,
        it could refer entPhysicalIndex in the Entity MIB to get entity
        information.

        GLOSSARY

        IEEE 802.11
        Standard to encourage interoperability among
        wireless networking equipment.

        Access point (AP)
        Transmitter/receiver (transceiver) device
        that commonly connects and transports data
        between a wireless network and a wired network.

        Access control (AC)
        To control and manage multi-APs, it will bridge
        wireless and wired network.

        Radio
        The chip set to receive and send wireless signal.

        Fat AP
        Applied in the home, SOHO and so on, and it could
        independently work without help from AC.

        Fit AP
        Applied in the enterprise environment, it will work
        under the control and management from AC.

        Control And Provisioning of Wireless Access Points Protocol
        The short name of protocol is CAPWAP. AC will control
        and manage AP by CAPWAP tunnel protocol defined by IETF.
        Also, a data tunnel will be set up between AC and AP.

        Basic Service Set
        The IEEE 802.11 BSS of an AP comprises of the
        stations directly associating with the AP. It will
        be identified by BSSID."

    REVISION "200712211800Z"        -- Dec 21, 2007 at 18:00 GMT
    DESCRIPTION
        "Modified to add new nodes."
    REVISION "200706191800Z"        -- June 19, 2007 at 18:00 GMT
    DESCRIPTION
        "Modified to add new table and new nodes."
    REVISION "200704272000Z"        -- Apr 27, 2007 at 20:00 GMT
    DESCRIPTION
        "Modified to fix some issue."
    REVISION "200605101900Z"        -- May 10, 2006 at 19:00 GMT
    DESCRIPTION
        "The initial revision of this MIB module."
    ::= { h3cDot11 1 }

-- *****************************************************************************
-- *  Major sections
-- *****************************************************************************

--  AC Object Group Attributes
--  DEFINED AS " The group provides AC information like MAC Mode and so on,
--  also could refer to software version and hardware version kept
--  by Entity MIB by Physical index"

h3cDot11ACObjectGroup OBJECT IDENTIFIER     ::= { h3cDot11ACMT 1 }
h3cDot11ACObject OBJECT IDENTIFIER          ::= { h3cDot11ACObjectGroup 1 }
h3cDot11ACLoadInfo OBJECT IDENTIFIER        ::= { h3cDot11ACObjectGroup 2 }
h3cDot11WLANAssocStatisInfo OBJECT IDENTIFIER  ::= { h3cDot11ACObjectGroup 3 }


--  AC CAPWAP tunnel Group Attributes
--  DEFINED AS "The group provides CAPWAP tunnel information"

h3cDot11CAPWAPTunnelGroup OBJECT IDENTIFIER  ::= { h3cDot11ACMT 2 }

--  AC CAPWAP Notification
--  DEFINED AS "The notification for AC Management"

h3cDot11ACMtNotifyGroup OBJECT IDENTIFIER    ::= { h3cDot11ACMT 3 }

-- *****************************************************************************
-- *  h3cDot11ACObject element Definition
-- *****************************************************************************
h3cDot11CurrentACMACMode OBJECT-TYPE
    SYNTAX      H3cDot11MACModeType
    MAX-ACCESS  read-only
    STATUS      current
    DESCRIPTION
        "Represents which MAC mode defined in the CAPWAP draft is in use
        for the AC."
    DEFVAL      { split }
    ::= { h3cDot11ACObject 1 }

h3cDot11MaxAPNumPermitted OBJECT-TYPE
    SYNTAX      Integer32
    MAX-ACCESS  read-only
    STATUS      current
    DESCRIPTION
        "Represents the maximum number of AP connection permitted
        for one AC."
    ::= { h3cDot11ACObject 2 }

h3cDot11MaxStationNumPermitted OBJECT-TYPE
    SYNTAX      Integer32
    MAX-ACCESS  read-only
    STATUS      current
    DESCRIPTION
        "Represents the maximum number of station connection
        permitted for one AC."
    ::= { h3cDot11ACObject 3 }
-- *****************************************************************************
-- *  End of h3cDot11ACObject element Definition
-- *****************************************************************************

-- *****************************************************************************
-- *  h3cDot11ACLoadInfo element Definition
-- *****************************************************************************
h3cDot11APConnectCount OBJECT-TYPE
    SYNTAX      Integer32
    MAX-ACCESS  read-only
    STATUS      current
    DESCRIPTION
        "Represents the total number of APs which are connecting to AC."
    ::= { h3cDot11ACLoadInfo 1 }

h3cDot11StationConnectCount OBJECT-TYPE
    SYNTAX      Integer32
    MAX-ACCESS  read-only
    STATUS      current
    DESCRIPTION
        "Represents the total number of stations which are accessing the
        WLAN service through AC."
    ::= { h3cDot11ACLoadInfo 2 }
-- *****************************************************************************
-- *  End of h3cDot11ACLoad element Definition
-- *****************************************************************************

-- *****************************************************************************
-- *  h3cDot11WLANAssocStatisInfo Definition
-- *****************************************************************************
h3cDot11StationAssocSum OBJECT-TYPE
    SYNTAX      Counter32
    MAX-ACCESS  read-only
    STATUS      current
    DESCRIPTION
        "Represents the total number of station association."
    ::= { h3cDot11WLANAssocStatisInfo 1 }

h3cDot11StationAssocFailSum OBJECT-TYPE
    SYNTAX      Counter32
    MAX-ACCESS  read-only
    STATUS      current
    DESCRIPTION
        "Represents the total number of station association failure."
    ::= { h3cDot11WLANAssocStatisInfo 2 }

h3cDot11StationReassocSum OBJECT-TYPE
    SYNTAX      Counter32
    MAX-ACCESS  read-only
    STATUS      current
    DESCRIPTION
        "Represents the total number of station reassociation."
    ::= { h3cDot11WLANAssocStatisInfo 3 }

h3cDot11StationAssocRejectedSum OBJECT-TYPE
    SYNTAX      Counter32
    MAX-ACCESS  read-only
    STATUS      current
    DESCRIPTION
        "Represents the total number of station association rejected on
        account of resource limit."
    ::= { h3cDot11WLANAssocStatisInfo 4 }

h3cDot11StationExDeAuthenSum OBJECT-TYPE
    SYNTAX      Counter32
    MAX-ACCESS  read-only
    STATUS      current
    DESCRIPTION
        "Represents the total number of exceptional station deauthentication
        (Without sending a deauthentication to AP)."
    ::= { h3cDot11WLANAssocStatisInfo 5 }

h3cDot11StationCurAssocSum OBJECT-TYPE
    SYNTAX      Integer32
    MAX-ACCESS  read-only
    STATUS      current
    DESCRIPTION
        "Represents the total number of current associated stations."
    ::= { h3cDot11WLANAssocStatisInfo 6 }
-- *****************************************************************************
-- *  End of h3cDot11WLANAssocStatisInfo Definition
-- *****************************************************************************

-- *****************************************************************************
-- *  h3cDot11CAPWAPTunnelTable Definition
-- *****************************************************************************
h3cDot11CAPWAPTunnelTable OBJECT-TYPE
    SYNTAX      SEQUENCE OF H3cDot11CAPWAPTunnelEntry
    MAX-ACCESS  not-accessible
    STATUS      current
    DESCRIPTION
        "The table will list all the APs which are connecting to the AC
        by the CAPWAP tunnel protocol."
    ::= { h3cDot11CAPWAPTunnelGroup 1 }

h3cDot11CAPWAPTunnelEntry OBJECT-TYPE
    SYNTAX      H3cDot11CAPWAPTunnelEntry
    MAX-ACCESS  not-accessible
    STATUS      current
    DESCRIPTION
        "Each entry contains information of data tunnel and control
        tunnel of AP which is connecting to AC."
    INDEX
        {
            h3cDot11CurrTunnelAPID
        }
    ::= { h3cDot11CAPWAPTunnelTable 1 }

H3cDot11CAPWAPTunnelEntry ::= SEQUENCE
    {
        h3cDot11CurrTunnelAPID       H3cDot11ObjectIDType,
        h3cDot11CtrlTunnelCurrSec    H3cDot11TunnelSecSchemType,
        h3cDot11CtrlTunnelUpTime     Integer32,
        h3cDot11DataTunnelCurrSec    H3cDot11TunnelSecSchemType,
        h3cDot11DataTunnelUpTime     Integer32
    }

h3cDot11CurrTunnelAPID OBJECT-TYPE
    SYNTAX      H3cDot11ObjectIDType
    MAX-ACCESS  accessible-for-notify
    STATUS      current
    DESCRIPTION
        "To uniquely identify the CAPWAP tunnel set up between the AP
        identified by APID and a specific AC."
    ::= { h3cDot11CAPWAPTunnelEntry 1 }

h3cDot11CtrlTunnelCurrSec OBJECT-TYPE
    SYNTAX      H3cDot11TunnelSecSchemType
    MAX-ACCESS  read-only
    STATUS      current
    DESCRIPTION
        "Represents what security scheme is in use for
        control tunnel."
    DEFVAL      { cleartxt }
    ::= { h3cDot11CAPWAPTunnelEntry 2 }

h3cDot11CtrlTunnelUpTime OBJECT-TYPE
    SYNTAX      Integer32
    UNITS       "second"
    MAX-ACCESS  read-only
    STATUS      current
    DESCRIPTION
        "Represents how long for control tunnel up. If the value is zero,
        then tunnel is not set up."
    ::= { h3cDot11CAPWAPTunnelEntry 3 }

h3cDot11DataTunnelCurrSec OBJECT-TYPE
    SYNTAX      H3cDot11TunnelSecSchemType
    MAX-ACCESS  read-only
    STATUS      current
    DESCRIPTION
        "Represents what security scheme is in use for
        data tunnel."
    DEFVAL      { cleartxt }
    ::= { h3cDot11CAPWAPTunnelEntry 4 }

h3cDot11DataTunnelUpTime OBJECT-TYPE
    SYNTAX      Integer32
    UNITS       "second"
    MAX-ACCESS  read-only
    STATUS      current
    DESCRIPTION
        "Represents how long for data tunnel up.
        If the value is zero, then tunnel is not set up."
    ::= { h3cDot11CAPWAPTunnelEntry 5 }
-- *****************************************************************************
-- *    End of h3cDot11CAPWAPTunnelTable  TABLE
-- *****************************************************************************

-- *****************************************************************************
-- *     Notifications OF h3cDot11ACMtNotifyGroup
-- *****************************************************************************
-- AC Management Notification

        h3cDot11ACMtTraps OBJECT IDENTIFIER
    ::= { h3cDot11ACMtNotifyGroup 0 }

h3cDot11ACMtTunnelSetupTrap NOTIFICATION-TYPE
    OBJECTS
        {
            h3cDot11CurrTunnelAPID,
            h3cDot11ACMtTrapTunlUpInfo
        }
    STATUS      current
    DESCRIPTION
        "This notification is sent by AC when CAPWAP tunnel becomes down.
        By this way, NMS will immediately know tunnel down event.
        It is unnecessary to identify whether it is control or data
        tunnel."
    ::= { h3cDot11ACMtTraps 1 }

h3cDot11ACMtTunnelDownTrap NOTIFICATION-TYPE
    OBJECTS
        {
            h3cDot11CurrTunnelAPID,
            h3cDot11ACMtTrapTunlDwnInfo
        }
    STATUS      current
    DESCRIPTION
        "This notification is sent by AC when CAPWAP tunnel becomes down.
        By this way, NMS will immediately know tunnel down event.
        It is unnecessary to identify whether it is control or data
        tunnel."
    ::= { h3cDot11ACMtTraps 2 }

-- AC Management Notification Variable object

        h3cDot11ACMtTrapVarObjects OBJECT IDENTIFIER
    ::= { h3cDot11ACMtNotifyGroup 1 }

h3cDot11ACMtTrapTunlDwnInfo OBJECT-TYPE
    SYNTAX      INTEGER
        {
            tunnelTimeout(1),
            keyUpdateFailure(2),
            apReset(3),
            apCrash(4),
            apDeleted(5),
            apCfgChange(6)
        }
    MAX-ACCESS  accessible-for-notify
    STATUS      current
    DESCRIPTION
        "Represents the reason for tunnel down.
        The following values are supported:
        tunnelTimeout(1),     - When AC detects the tunnel is broken,
        - it will notify NMS.
        keyUpdateFailure(2),  - rekey process is failed, tunnel will
        - be broken.
        apReset(3),           - Administrator reset AP.
        apCrash(4),           - AP reboot for system crash.
        apDeleted(5)          - Delete AP from AC and trigger
        - tunnel down.
        apCfgChange(6)        - The configuration for AP was changed."
    ::= { h3cDot11ACMtTrapVarObjects 1 }

h3cDot11ACMtTrapTunlUpInfo OBJECT-TYPE
    SYNTAX      INTEGER
        {
            up(1)
        }
    MAX-ACCESS  accessible-for-notify
    STATUS      current
    DESCRIPTION
        "Represents the reason for tunnel up.
        The following values are supported:
        up(1)  - The AP joined AC.
        "
    ::= { h3cDot11ACMtTrapVarObjects 2 }
-- *****************************************************************************
-- *     End OF NotifyGroup
-- *****************************************************************************
END
