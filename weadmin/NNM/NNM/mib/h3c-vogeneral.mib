-- Copyright (C) 2004 by Huawei 3Com Technologies. All rights reserved.
--
-- Description: The purpose of this MIB file is to provide the definition of
--              voice general configuration.
-- Reference:
-- ==========================================================================
H3C-VOGENERAL-MIB DEFINITIONS ::= BEGIN
    IMPORTS
        OBJECT-TYPE, MODULE-IDENTITY, Integer32
            FROM SNMPv2-SMI
        RowStatus
             FROM SNMPv2-TC
        h3cVoice
            FROM HUAWEI-3COM-OID-MIB;


        h3cVoiceGeneral MODULE-IDENTITY
            LAST-UPDATED "200503150000Z"
            ORGANIZATION
                "Huawei-3COM Technologies Co., Ltd."
            CONTACT-INFO
                "PLAT Team Huawei 3Com Technologies co.,Ltd.
                Shang-Di Information Industry Base,
                Hai-Dian District Beijing P.R. China
                http://www.huawei-3com.com
                Zip:100085"
            DESCRIPTION
                "This MIB is to provide the definition of voice voice
                general configuration."
            REVISION "200503150000Z"
            DESCRIPTION
                "The initial version of this MIB file."
           ::= { h3cVoice 1 }




--===========================================================================
--                            h3cVoiceGeneralObjects
--
--===========================================================================
        h3cVoiceGeneralObjects OBJECT IDENTIFIER ::= { h3cVoiceGeneral 1 }

        h3cVoGeneralJitterLen OBJECT-TYPE
            SYNTAX Integer32 (0..10)
            MAX-ACCESS read-write
            STATUS current
            DESCRIPTION
                "This object indicates the length of the Jitter buffer."
            ::= { h3cVoiceGeneralObjects 1 }


        h3cVoGeneralMatchPolicy OBJECT-TYPE
            SYNTAX INTEGER
                {
                long(1),
                short(2)
                }
            MAX-ACCESS read-write
            STATUS current
            DESCRIPTION
                "This object indicates the policy of number matching."
            ::= { h3cVoiceGeneralObjects 2 }


        h3cVoGeneralDataStatistics OBJECT-TYPE
            SYNTAX INTEGER
                {
                enable(1),
                disable(2)
                }
            MAX-ACCESS read-write
            STATUS current
            DESCRIPTION
                "This object indicates whether the data statistics is enabled."
            DEFVAL { disable }
            ::= { h3cVoiceGeneralObjects 5 }


        h3cVoGeneralDialTerminator OBJECT-TYPE
            SYNTAX OCTET STRING
            MAX-ACCESS read-write
            STATUS current
            DESCRIPTION
                "This object indicates the global character, which is used to
                notify gateway that dialing is completed."
            ::= { h3cVoiceGeneralObjects 7 }


        h3cVoGeneralCallStart OBJECT-TYPE
            SYNTAX INTEGER
                {
                fast(1),
                normal(2)
                }
            MAX-ACCESS read-write
            STATUS current
            DESCRIPTION
                "This object indicates whether to support the FAST START mode
                which the caller side initiates."
            ::= { h3cVoiceGeneralObjects 8 }


        h3cVoGeneralCalledTunnel OBJECT-TYPE
            SYNTAX INTEGER
                {
                enable(1),
                disable(2)
                }
            MAX-ACCESS read-write
            STATUS current
            DESCRIPTION
                "This object indicates whether the called tunnel function
                is enabled."
            ::= { h3cVoiceGeneralObjects 9 }


        h3cVoGeneralSpecialService OBJECT-TYPE
            SYNTAX INTEGER
                {
                enable(1),
                disable(2)
                }
            MAX-ACCESS read-write
            STATUS current
            DESCRIPTION
                "This object indicates whether special service number
                function is enabled."
            ::= { h3cVoiceGeneralObjects 10 }


        h3cVoGeneralPeerSearchStop OBJECT-TYPE
            SYNTAX Integer32
            MAX-ACCESS read-write
            STATUS current
            DESCRIPTION
                "This object indicates the maximum amount of the entities which
                the system will scan when a call has been initiated."
            ::= { h3cVoiceGeneralObjects 12 }


        h3cVoGeneralPeerSelectOrderRule OBJECT-TYPE
            SYNTAX INTEGER
                {
                epr(1),
                epl(2),
                elp(3),
                elr(4),
                per(5),
                pel(6),
                ple(7),
                plr(8),
                lep(9),
                ler(10),
                lpe(11),
                lpr(12),
                er(13),
                pr(14),
                lr(15),
                explicitMatch(16),
                priority(17),
                random(18),
                longestNoUse(19),
                ep(20),
                el(21),
                pe(22),
                pl(23),
                le(24),
                lp(25)
                }
            MAX-ACCESS read-write
            STATUS current
            DESCRIPTION
                "This object indicates the rule order applied in voice
                entity selection.
                epr(1)  --- explicit match, priority, random
                epl(2)  --- explicit match, priority, longest no use
                elp(3)  --- explicit match, longest no use, priority
                elr(4)  --- explicit match, longest no use, random
                per(5)  --- priority, explicit match, random
                pel(6)  --- priority, explicit match, longest no use
                ple(7)  --- priority, longest no use, explicit match
                plr(8)  --- priority, longest no use, random
                lep(9)  --- longest no use, explicit match, priority
                ler(10) --- longest no use, explicit match, random
                lpe(11) --- longest no use, priority, explicit match
                lpr(12) --- longest no use, priority, random
                er(13)  --- explicit match, random
                pr(14)  --- priority, random
                lr(15)  --- longest no use, random
                explicitMatch(16)    --- explicit match
                priority(17)         --- priority
                random(18)           --- random
                longestNoUse(19)     --- longest no use
                ep(20)  --- explicit match, priority
                el(21)  --- explicit match, longest no use
                pe(22)  --- priority, explicit match
                pl(23)  --- priority, longest no use
                le(24)  --- longest no use, explicit match
                lp(25)  --- longest no use, priority
                "
            ::= { h3cVoiceGeneralObjects 13 }


        h3cVoGeneralPeerSelectTypePriority OBJECT-TYPE
            SYNTAX INTEGER
                {
                noneType(1),
                voipPotsVofr(2),
                voipVofrPots(3),
                potsVoipVofr(4),
                potsVofrVoip(5),
                vofrPotsVoip(6),
                vofrVoipPots(7)
                }
            MAX-ACCESS read-write
            STATUS current
            DESCRIPTION
                "This object indicates the priority-ranked type of voice entity.
                                         1ST  2DN  3RD
                noneType(1)          --- NONE TYPE
                voipPotsVofr(2)      --- VOIP POTS VOFR
                voipVofrPots(3)      --- VOIP VOFR POTS
                potsVoipVofr(4)      --- POTS VOIP VOFR
                potsVofrVoip(5)      --- POTS VOFR VOIP
                vofrPotsVoip(6)      --- VOFR POTS VOIP
                vofrVoipPots(7)      --- VOFR VOIP POTS
                "
            ::= { h3cVoiceGeneralObjects 14 }

        h3cVoGeneralDscpSignal OBJECT-TYPE
            SYNTAX Integer32(0..63)
            MAX-ACCESS read-write
            STATUS current
            DESCRIPTION
                "This object indicates DSCP(Different Service Code Point)
                signal value."
            ::= { h3cVoiceGeneralObjects 15 }

        h3cVoGeneralDscpMedia OBJECT-TYPE
            SYNTAX Integer32(0..63)
            MAX-ACCESS read-write
            STATUS current
            DESCRIPTION
                "This object indicates DSCP(Different Service Code Point)
                media value."
            ::= { h3cVoiceGeneralObjects 16 }


--===========================================================================
--                            h3cVoNumSubstTable
--
--===========================================================================
        h3cVoiceNumberSubstGroup OBJECT IDENTIFIER ::= { h3cVoiceGeneral 4 }

        h3cVoNumSubstTable OBJECT-TYPE
            SYNTAX SEQUENCE OF H3CVoNumSubstEntry
            MAX-ACCESS not-accessible
            STATUS current
            DESCRIPTION
                "The table contains the number substitute rule."
            ::= { h3cVoiceNumberSubstGroup 1 }


        h3cVoNumSubstEntry OBJECT-TYPE
            SYNTAX H3CVoNumSubstEntry
            MAX-ACCESS not-accessible
            STATUS current
            DESCRIPTION
                "The entry of h3cVoNumSubstTable."
            INDEX { h3cVoNumSubstIndex }
            ::= { h3cVoNumSubstTable 1 }

        H3CVoNumSubstEntry ::= SEQUENCE
            {
            h3cVoNumSubstIndex
                Integer32,
            h3cVoNumSubstFirstRule
                Integer32,
            h3cVoNumSubstDotMatchRule
                INTEGER,
            h3cVoNumSubstRowStatus
                RowStatus
            }


        h3cVoNumSubstIndex OBJECT-TYPE
            SYNTAX Integer32(1..2147483647)
            MAX-ACCESS not-accessible
            STATUS current
            DESCRIPTION
                "The index of the number substitute rule table."
            ::= { h3cVoNumSubstEntry 1 }


        h3cVoNumSubstFirstRule  OBJECT-TYPE
            SYNTAX Integer32
            MAX-ACCESS read-create
            STATUS current
            DESCRIPTION
                "This object indicates the first rule to be used."
            ::= { h3cVoNumSubstEntry 2 }


        h3cVoNumSubstDotMatchRule  OBJECT-TYPE
            SYNTAX INTEGER
                {
                endOnly(1),
                leftRight(2),
                rightLeft(3)
                }
            MAX-ACCESS read-create
            STATUS current
            DESCRIPTION
                "This object indicates the dot wildcard match rule.
                endOnly   - only end of E.164 number (input format)
                leftRight - match form left to right (input format)
                rightLeft - match form right to left (input format)
                "
            ::= { h3cVoNumSubstEntry 3 }


        h3cVoNumSubstRowStatus OBJECT-TYPE
            SYNTAX RowStatus
            MAX-ACCESS read-create
            STATUS current
            DESCRIPTION
                "This object is used to create, delete or modify a row in
                this table."
            ::= { h3cVoNumSubstEntry 4 }


--===========================================================================
--                         h3cVoNumSubstRuleTable
--
--===========================================================================
        h3cVoNumSubstRuleTable OBJECT-TYPE
            SYNTAX SEQUENCE OF H3CVoNumSubstRuleEntry
            MAX-ACCESS not-accessible
            STATUS current
            DESCRIPTION
                "The table contains the number-substitute rule information."
            ::= { h3cVoiceNumberSubstGroup 2 }

        h3cVoNumSubstRuleEntry OBJECT-TYPE
            SYNTAX H3CVoNumSubstRuleEntry
            MAX-ACCESS not-accessible
            STATUS current
            DESCRIPTION
                "The entry of a single number substitute rule."
            INDEX { h3cVoNumSubstIndex,h3cVoNumSubstRuleIndex }
            ::= { h3cVoNumSubstRuleTable 1 }

        H3CVoNumSubstRuleEntry ::=
            SEQUENCE{
                h3cVoNumSubstRuleIndex
                    Integer32,
                h3cVoNumSubstRuleInputFormat
                    OCTET STRING,
                h3cVoNumSubstRuleOutputFormat
                    OCTET STRING,
                h3cVoNumSubstRuleRowStatus
                    RowStatus
            }


        h3cVoNumSubstRuleIndex OBJECT-TYPE
        SYNTAX Integer32(0..127)
        MAX-ACCESS not-accessible
        STATUS current
        DESCRIPTION
            "The index of a number-substitute rule."
        ::= { h3cVoNumSubstRuleEntry 1 }


        h3cVoNumSubstRuleInputFormat OBJECT-TYPE
        SYNTAX OCTET STRING
        MAX-ACCESS read-create
        STATUS current
        DESCRIPTION
            "This object specifies the match format for input."
        ::= { h3cVoNumSubstRuleEntry 2 }


        h3cVoNumSubstRuleOutputFormat OBJECT-TYPE
        SYNTAX OCTET STRING
        MAX-ACCESS read-create
        STATUS current
        DESCRIPTION
            "This object specifies the output format."
        ::= { h3cVoNumSubstRuleEntry 3 }


        h3cVoNumSubstRuleRowStatus OBJECT-TYPE
        SYNTAX RowStatus
        MAX-ACCESS read-create
        STATUS current
        DESCRIPTION
            "This object is used to create, delete or modify a row in
            this table."
        ::= { h3cVoNumSubstRuleEntry 4 }


--===========================================================================
--                            h3cVoMaxCallTable
--
--===========================================================================
        h3cVoMaxCallTable OBJECT-TYPE
        SYNTAX SEQUENCE OF H3CVoMaxCallEntry
        MAX-ACCESS not-accessible
        STATUS current
        DESCRIPTION
            "The table contains the maximum number of the calls which
            can be established simultaneously."
        ::= { h3cVoiceGeneral 5 }


        h3cVoMaxCallEntry OBJECT-TYPE
        SYNTAX H3CVoMaxCallEntry
        MAX-ACCESS not-accessible
        STATUS current
        DESCRIPTION
            "The entry of the max call table."
        INDEX { h3cVoMaxCallTableIndex }
        ::= { h3cVoMaxCallTable 1 }

        H3CVoMaxCallEntry ::=
            SEQUENCE {
                h3cVoMaxCallTableIndex
                    Integer32,
                h3cVoMaxCallValue
                    Integer32,
                h3cVoMaxCallTableRowStatus
                    RowStatus
            }


        h3cVoMaxCallTableIndex OBJECT-TYPE
            SYNTAX Integer32(1..2147483647)
            MAX-ACCESS not-accessible
            STATUS current
            DESCRIPTION
                "The index uniquely identifies a single maximum call value."
            ::= { h3cVoMaxCallEntry 1 }


        h3cVoMaxCallValue OBJECT-TYPE
        SYNTAX Integer32(0..120)
        MAX-ACCESS read-create
        STATUS current
        DESCRIPTION
            "This object specifies a single maximum call value."
        ::= { h3cVoMaxCallEntry 2 }


        h3cVoMaxCallTableRowStatus OBJECT-TYPE
        SYNTAX RowStatus
        MAX-ACCESS read-create
        STATUS current
        DESCRIPTION
            "This object is used to create, delete or modify a row in
            this table.
            Note: when create a new row, h3cVoMaxCallValue must be configured."
        ::= { h3cVoMaxCallEntry 3 }


--===========================================================================
--                      h3cVoInCallingNumSubstTable
--
--===========================================================================
        h3cVoInCallingNumSubstTable OBJECT-TYPE
        SYNTAX SEQUENCE OF H3CVoInCallingNumSubstEntry
        MAX-ACCESS not-accessible
        STATUS current
        DESCRIPTION
            "This table contains the rules of caller number substitute for
            incoming call."
        ::= { h3cVoiceGeneral 6 }


        h3cVoInCallingNumSubstEntry OBJECT-TYPE
        SYNTAX H3CVoInCallingNumSubstEntry
        MAX-ACCESS not-accessible
        STATUS current
        DESCRIPTION
            "The entry of h3cVoInCallingNumSubstTable."
        INDEX { h3cVoInCallingNumSubstIndex }
        ::= { h3cVoInCallingNumSubstTable 1 }

        H3CVoInCallingNumSubstEntry ::=
            SEQUENCE {
                h3cVoInCallingNumSubstIndex
                    Integer32,
                h3cVoInCallingSubstRowStatus
                    RowStatus
            }


        h3cVoInCallingNumSubstIndex OBJECT-TYPE
        SYNTAX Integer32(1..2147483647)
        MAX-ACCESS not-accessible
        STATUS current
        DESCRIPTION
            "The index of incoming call substitute table."
        ::= { h3cVoInCallingNumSubstEntry 1 }


        h3cVoInCallingSubstRowStatus OBJECT-TYPE
        SYNTAX RowStatus
        MAX-ACCESS read-create
        STATUS current
        DESCRIPTION
            "This object is used to create, delete or modify a row in
            this table."
        ::= { h3cVoInCallingNumSubstEntry 2 }


--===========================================================================
--                      h3cVoInCalledNumSubstTable
--
--===========================================================================
        h3cVoInCalledNumSubstTable OBJECT-TYPE
        SYNTAX SEQUENCE OF H3CVoInCalledNumSubstEntry
        MAX-ACCESS not-accessible
        STATUS current
        DESCRIPTION
            "This table contains the rules of called number substitute for
            incoming call."
        ::= { h3cVoiceGeneral 7 }


        h3cVoInCalledNumSubstEntry OBJECT-TYPE
        SYNTAX H3CVoInCalledNumSubstEntry
        MAX-ACCESS not-accessible
        STATUS current
        DESCRIPTION
            "The entry of h3cVoInCalledNumSubstTable."
        INDEX { h3cVoInCalledNumSubstIndex }
        ::= { h3cVoInCalledNumSubstTable 1 }

        H3CVoInCalledNumSubstEntry ::=
            SEQUENCE {
                h3cVoInCalledNumSubstIndex
                    Integer32,
                h3cVoInCalledSubstRowStatus
                    RowStatus
            }


        h3cVoInCalledNumSubstIndex OBJECT-TYPE
            SYNTAX Integer32(1..2147483647)
            MAX-ACCESS not-accessible
            STATUS current
            DESCRIPTION
                "The index of incomed call substitute table."
            ::= { h3cVoInCalledNumSubstEntry 1 }


        h3cVoInCalledSubstRowStatus OBJECT-TYPE
        SYNTAX RowStatus
        MAX-ACCESS read-create
        STATUS current
        DESCRIPTION
            "This object is used to create, delete or modify a row in
            this table."
        ::= { h3cVoInCalledNumSubstEntry 2 }


--===========================================================================
--                      h3cVoOutCallingNumSubstTable
--
--===========================================================================
        h3cVoOutCallingNumSubstTable OBJECT-TYPE
        SYNTAX SEQUENCE OF H3CVoOutCallingNumSubstEntry
        MAX-ACCESS not-accessible
        STATUS current
        DESCRIPTION
            "This table contains the rules of caller number substitute for
            outgoing call."
        ::= { h3cVoiceGeneral 8 }


        h3cVoOutCallingNumSubstEntry OBJECT-TYPE
        SYNTAX H3CVoOutCallingNumSubstEntry
        MAX-ACCESS not-accessible
        STATUS current
        DESCRIPTION
            "The entry of h3cVoOutCallingNumSubstTable."
        INDEX { h3cVoOutCallingNumSubstIndex }
        ::= { h3cVoOutCallingNumSubstTable 1 }


        H3CVoOutCallingNumSubstEntry ::=
            SEQUENCE {
                h3cVoOutCallingNumSubstIndex
                    Integer32,
                h3cVoOutCallingSubstRowStatus
                    RowStatus
            }


        h3cVoOutCallingNumSubstIndex OBJECT-TYPE
        SYNTAX Integer32(1..2147483647)
        MAX-ACCESS not-accessible
        STATUS current
        DESCRIPTION
            "The index of outgoing calling substitute table."
        ::= { h3cVoOutCallingNumSubstEntry 1 }


        h3cVoOutCallingSubstRowStatus OBJECT-TYPE
        SYNTAX RowStatus
        MAX-ACCESS read-create
        STATUS current
        DESCRIPTION
            "This object is used to create, delete or modify a row in
            this table."
        ::= { h3cVoOutCallingNumSubstEntry 2 }



--===========================================================================
--                      h3cVoOutCalledNumSubstTable
--
--===========================================================================
        h3cVoOutCalledNumSubstTable OBJECT-TYPE
        SYNTAX SEQUENCE OF H3CVoOutgoingCalledNumSubstEntry
        MAX-ACCESS not-accessible
        STATUS current
        DESCRIPTION
            "This table contains the rules of called number substitute for
            outgoing call."
        ::= { h3cVoiceGeneral 9 }


        h3cVoOutgoingCalledNumSubstEntry OBJECT-TYPE
        SYNTAX H3CVoOutgoingCalledNumSubstEntry
        MAX-ACCESS not-accessible
        STATUS current
        DESCRIPTION
            "The entry of h3cVoOutCalledNumSubstTable."
        INDEX { h3cVoOutCalledNumSubstIndex }
        ::= { h3cVoOutCalledNumSubstTable 1 }

        H3CVoOutgoingCalledNumSubstEntry ::=
        SEQUENCE {
            h3cVoOutCalledNumSubstIndex
                Integer32,
            h3cVoOutCalledSubstRowStatus
                RowStatus
        }


        h3cVoOutCalledNumSubstIndex OBJECT-TYPE
        SYNTAX Integer32(1..2147483647)
        MAX-ACCESS not-accessible
        STATUS current
        DESCRIPTION
            "The index of outgoing called substitute table."
        ::= { h3cVoOutgoingCalledNumSubstEntry 1 }


        h3cVoOutCalledSubstRowStatus OBJECT-TYPE
            SYNTAX RowStatus
            MAX-ACCESS read-create
            STATUS current
            DESCRIPTION
                "This object is used to create, delete or modify a row in
                this table."
            ::= { h3cVoOutgoingCalledNumSubstEntry 2 }

    END
